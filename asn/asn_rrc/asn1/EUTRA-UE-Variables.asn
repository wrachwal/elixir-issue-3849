EUTRA-UE-Variables DEFINITIONS AUTOMATIC TAGS ::=

BEGIN

IMPORTS
    AbsoluteTimeInfo-r10,
    AreaConfiguration-r10,
    AreaConfiguration-v1130,
    CarrierFreqGERAN,
    CellIdentity,
    ConnEstFailReport-r11,
    SpeedStateScaleFactors,
    C-RNTI,
    LoggingDuration-r10,
    LoggingInterval-r10,
    LogMeasInfo-r10,
    MeasCSI-RS-Id-r12,
    MeasId,
    MeasId-v1250,
    MeasIdToAddModList,
    MeasIdToAddModListExt-r12,
    MeasObjectToAddModList,
    MeasObjectToAddModList-v9e0,
    MeasScaleFactor-r12,
    MobilityStateParameters,
    NeighCellConfig,
    PhysCellId,
    PhysCellIdCDMA2000,
    PhysCellIdGERAN,
    PhysCellIdUTRA-FDD,
    PhysCellIdUTRA-TDD,
    PLMN-Identity,
    PLMN-IdentityList3-r11,
    QuantityConfig,
    ReportConfigToAddModList,
    RLF-Report-r9,
    TargetMBSFN-AreaList-r12,
    TraceReference-r10,
    VisitedCellInfoList-r12,
    maxCellMeas,
    maxCSI-RS-Meas-r12,
    maxMeasId,
    maxMeasId-r12
FROM EUTRA-RRC-Definitions;

VarConnEstFailReport-r11 ::=        SEQUENCE {
    connEstFailReport-r11               ConnEstFailReport-r11,
    plmn-Identity-r11                   PLMN-Identity
}

VarLogMeasConfig-r10 ::=                SEQUENCE {
    areaConfiguration-r10           AreaConfiguration-r10       OPTIONAL,
    loggingDuration-r10             LoggingDuration-r10,
    loggingInterval-r10             LoggingInterval-r10
}

VarLogMeasConfig-r11 ::=        SEQUENCE {
    areaConfiguration-r10           AreaConfiguration-r10       OPTIONAL,
    areaConfiguration-v1130         AreaConfiguration-v1130     OPTIONAL,
    loggingDuration-r10             LoggingDuration-r10,
    loggingInterval-r10             LoggingInterval-r10
}

VarLogMeasConfig-r12 ::=        SEQUENCE {
    areaConfiguration-r10           AreaConfiguration-r10       OPTIONAL,
    areaConfiguration-v1130         AreaConfiguration-v1130     OPTIONAL,
    loggingDuration-r10             LoggingDuration-r10,
    loggingInterval-r10             LoggingInterval-r10,
    targetMBSFN-AreaList-r12        TargetMBSFN-AreaList-r12    OPTIONAL
}

VarLogMeasReport-r10 ::=                SEQUENCE {
    traceReference-r10                  TraceReference-r10,
    traceRecordingSessionRef-r10            OCTET STRING (SIZE (2)),
    tce-Id-r10                          OCTET STRING (SIZE (1)),
    plmn-Identity-r10                   PLMN-Identity,
    absoluteTimeInfo-r10                AbsoluteTimeInfo-r10,
    logMeasInfoList-r10                 LogMeasInfoList2-r10
}

VarLogMeasReport-r11 ::=            SEQUENCE {
    traceReference-r10                  TraceReference-r10,
    traceRecordingSessionRef-r10        OCTET STRING (SIZE (2)),
    tce-Id-r10                          OCTET STRING (SIZE (1)),
    plmn-IdentityList-r11               PLMN-IdentityList3-r11,
    absoluteTimeInfo-r10                AbsoluteTimeInfo-r10,
    logMeasInfoList-r10                 LogMeasInfoList2-r10
}

LogMeasInfoList2-r10 ::=                SEQUENCE (SIZE (1..maxLogMeas-r10)) OF LogMeasInfo-r10

VarMeasConfig ::=                   SEQUENCE {
    -- Measurement identities
    measIdList                          MeasIdToAddModList                  OPTIONAL,
    measIdListExt-r12                   MeasIdToAddModListExt-r12           OPTIONAL,
    -- Measurement objects
    measObjectList                      MeasObjectToAddModList              OPTIONAL,
    measObjectList-v9i0                 MeasObjectToAddModList-v9e0         OPTIONAL,
    -- Reporting configurations
    reportConfigList                    ReportConfigToAddModList            OPTIONAL,
    -- Other parameters
    quantityConfig                      QuantityConfig                      OPTIONAL,
    measScaleFactor-r12                 MeasScaleFactor-r12                 OPTIONAL,
    s-Measure                           INTEGER (-140..-44)                 OPTIONAL,
    speedStatePars                      CHOICE {
        release                             NULL,
        setup                               SEQUENCE {
            mobilityStateParameters             MobilityStateParameters,
            timeToTrigger-SF                    SpeedStateScaleFactors
        }
    }                                                                       OPTIONAL,
    allowInterruptions-r11          BOOLEAN                             OPTIONAL
}

VarMeasReportList ::=               SEQUENCE (SIZE (1..maxMeasId)) OF VarMeasReport
VarMeasReportList-r12 ::=           SEQUENCE (SIZE (1..maxMeasId-r12)) OF VarMeasReport

VarMeasReport ::=                   SEQUENCE {
    -- List of measurement that have been triggered
    measId                              MeasId,
    measId-v1250                        MeasId-v1250                    OPTIONAL,
    cellsTriggeredList                  CellsTriggeredList              OPTIONAL,
    csi-RS-TriggeredList-r12            CSI-RS-TriggeredList-r12        OPTIONAL,
    numberOfReportsSent                 INTEGER
}

CellsTriggeredList ::=              SEQUENCE (SIZE (1..maxCellMeas)) OF CHOICE {
    physCellIdEUTRA                         PhysCellId,
    physCellIdUTRA                          CHOICE {
        fdd                                     PhysCellIdUTRA-FDD,
        tdd                                     PhysCellIdUTRA-TDD
    },
    physCellIdGERAN                         SEQUENCE {
        carrierFreq                             CarrierFreqGERAN,
        physCellId                              PhysCellIdGERAN
    },
    physCellIdCDMA2000                      PhysCellIdCDMA2000
}

CSI-RS-TriggeredList-r12 ::=        SEQUENCE (SIZE (1..maxCSI-RS-Meas-r12)) OF MeasCSI-RS-Id-r12

VarMobilityHistoryReport-r12 ::=    VisitedCellInfoList-r12

VarRLF-Report-r10 ::=               SEQUENCE {
    rlf-Report-r10                          RLF-Report-r9,
    plmn-Identity-r10                       PLMN-Identity
}

VarRLF-Report-r11 ::=               SEQUENCE {
    rlf-Report-r10                      RLF-Report-r9,
    plmn-IdentityList-r11               PLMN-IdentityList3-r11
}

VarShortMAC-Input ::=                   SEQUENCE {
    cellIdentity                            CellIdentity,
    physCellId                              PhysCellId,
    c-RNTI                                  C-RNTI
}
maxLogMeas-r10              INTEGER ::= 4060-- Maximum number of logged measurement entries
                                            --  that can be stored by the UE

END
