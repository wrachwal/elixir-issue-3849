-- **************************************************************
--
-- PDU definitions for X2AP.
--
-- **************************************************************

X2AP-PDU-Contents {
itu-t (0) identified-organization (4) etsi (0) mobileDomain (0) 
eps-Access (21) modules (3) x2ap (2) version1 (1) x2ap-PDU-Contents (1) }

DEFINITIONS AUTOMATIC TAGS ::= 

BEGIN

-- **************************************************************
--
-- IE parameter types from other modules.
--
-- **************************************************************

IMPORTS
    ABSInformation,
    ABS-Status,
    AS-SecurityInformation,
    Cause,
    CompositeAvailableCapacityGroup,
    COUNTvalue,
    CriticalityDiagnostics,
    CRNTI,
    CSGMembershipStatus,
    CSG-Id,
    DeactivationIndication,
    DL-Forwarding,
    DynamicDLTransmissionInformation,
    ECGI,
    E-RAB-ID,
    E-RAB-Level-QoS-Parameters,
    E-RAB-List,
    EUTRANTraceID,
    GlobalENB-ID,
    GTPtunnelEndpoint,
    GUGroupIDList,
    GUMMEI,
    HandoverReportType,
    HandoverRestrictionList,
    Masked-IMEISV,
    InvokeIndication,
    LocationReportingInformation,
    MDT-Configuration,
    ManagementBasedMDTallowed,
    MDTPLMNList,
    Neighbour-Information,
    PCI,
    PDCP-SN,
    PLMN-Identity,
    ReceiveStatusofULPDCPSDUs,
    Registration-Request,
    RelativeNarrowbandTxPower,
    RadioResourceStatus,
    RRCConnReestabIndicator,
    RRCConnSetupIndicator,
    UE-RLF-Report-Container,
    RRC-Context,
    ServedCell-Information,
    ServedCells,
    ShortMAC-I,
    SRVCCOperationPossible,
    SubscriberProfileIDforRFP,
    TargetCellInUTRAN,
    TargeteNBtoSource-eNBTransparentContainer,
    TimeToWait,
    TraceActivation,
    TraceDepth,
    TransportLayerAddress,
    UEAggregateMaximumBitRate,
    UE-HistoryInformation,
    UE-HistoryInformationFromTheUE,
    UE-S1AP-ID,
    UESecurityCapabilities,
    UE-X2AP-ID,
    UL-HighInterferenceIndicationInfo,
    UL-InterferenceOverloadIndication,
    HWLoadIndicator,
    S1TNLLoadIndicator,
    Measurement-ID,
    ReportCharacteristics,
    MobilityParametersInformation,
    MobilityParametersModificationRange,
    ReceiveStatusOfULPDCPSDUsExtended,
    COUNTValueExtended,
    SubframeAssignment,
    ExtendedULInterferenceOverloadInfo,
    ExpectedUEBehaviour,
    SeNBSecurityKey,
    MeNBtoSeNBContainer,
    SeNBtoMeNBContainer,
    SCGChangeIndication,
    CoMPInformation,
    ReportingPeriodicityRSRPMR,
    RSRPMRList,
    UE-RLF-Report-Container-for-extended-bands
FROM X2AP-IEs

    PrivateIE-Container{},
    ProtocolExtensionContainer{},
    ProtocolIE-Container{},
    ProtocolIE-ContainerList{},
    ProtocolIE-ContainerPair{},
    ProtocolIE-ContainerPairList{},
    ProtocolIE-Single-Container{},
    X2AP-PRIVATE-IES,
    X2AP-PROTOCOL-EXTENSION,
    X2AP-PROTOCOL-IES,
    X2AP-PROTOCOL-IES-PAIR
FROM X2AP-Containers

    id-ABSInformation,
    id-ActivatedCellList,
    id-Cause,
    id-CellInformation,
    id-CellInformation-Item,
    id-CellMeasurementResult,
    id-CellMeasurementResult-Item,
    id-CellToReport,
    id-CellToReport-Item,
    id-CompositeAvailableCapacityGroup,
    id-CriticalityDiagnostics,
    id-DeactivationIndication,
    id-DynamicDLTransmissionInformation,
    id-E-RABs-Admitted-Item,
    id-E-RABs-Admitted-List,
    id-E-RABs-NotAdmitted-List,
    id-E-RABs-SubjectToStatusTransfer-List,
    id-E-RABs-SubjectToStatusTransfer-Item,
    id-E-RABs-ToBeSetup-Item,
    id-GlobalENB-ID,
    id-GUGroupIDList,
    id-GUGroupIDToAddList,
    id-GUGroupIDToDeleteList,
    id-GUMMEI-ID,
    id-Masked-IMEISV,
    id-InvokeIndication,
    id-New-eNB-UE-X2AP-ID,
    id-Old-eNB-UE-X2AP-ID,
    id-Registration-Request,
    id-ReportingPeriodicity,
    id-ServedCells,
    id-ServedCellsToActivate,
    id-ServedCellsToAdd,
    id-ServedCellsToModify,
    id-ServedCellsToDelete,
    id-SRVCCOperationPossible,
    id-TargetCell-ID,
    id-TargeteNBtoSource-eNBTransparentContainer,
    id-TimeToWait,
    id-TraceActivation,
    id-UE-ContextInformation,
    id-UE-HistoryInformation,
    id-UE-X2AP-ID,
    id-Measurement-ID,
    id-ReportCharacteristics,
    id-ENB1-Measurement-ID,
    id-ENB2-Measurement-ID,
    id-ENB1-Cell-ID,
    id-ENB2-Cell-ID,
    id-ENB2-Proposed-Mobility-Parameters,
    id-ENB1-Mobility-Parameters,
    id-ENB2-Mobility-Parameters-Modification-Range,
    id-FailureCellPCI,
    id-Re-establishmentCellECGI,
    id-FailureCellCRNTI,
    id-ShortMAC-I,
    id-SourceCellECGI,
    id-FailureCellECGI,
    id-HandoverReportType,
    id-UE-RLF-Report-Container,
    id-PartialSuccessIndicator,
    id-MeasurementInitiationResult-List,
    id-MeasurementInitiationResult-Item,
    id-MeasurementFailureCause-Item,
    id-CompleteFailureCauseInformation-List,
    id-CompleteFailureCauseInformation-Item,
    id-CSGMembershipStatus,
    id-CSG-Id,
    id-MDTConfiguration,
    id-ManagementBasedMDTallowed,
    id-ABS-Status,
    id-RRCConnSetupIndicator,
    id-RRCConnReestabIndicator,
    id-TargetCellInUTRAN,
    id-MobilityInformation,
    id-SourceCellCRNTI,
    id-ManagementBasedMDTPLMNList,
    id-ReceiveStatusOfULPDCPSDUsExtended,
    id-ULCOUNTValueExtended,
    id-DLCOUNTValueExtended,
    id-IntendedULDLConfiguration,
    id-ExtendedULInterferenceOverloadInfo,
    id-RNL-Header,
    id-x2APMessage,
    id-UE-HistoryInformationFromTheUE,
    id-ExpectedUEBehaviour,
    id-MeNB-UE-X2AP-ID,
    id-SeNB-UE-X2AP-ID,
    id-UE-SecurityCapabilities,
    id-SeNBSecurityKey,
    id-UEAggregateMaximumBitRate,
    id-ServingPLMN,
    id-E-RABs-ToBeAdded-List,
    id-E-RABs-ToBeAdded-Item,
    id-MeNBtoSeNBContainer,
    id-E-RABs-Admitted-ToBeAdded-List,
    id-E-RABs-Admitted-ToBeAdded-Item,
    id-SeNBtoMeNBContainer,
    id-ResponseInformationSeNBReconfComp,
    id-UE-ContextInformationSeNBModReq,
    id-E-RABs-ToBeAdded-ModReqItem,
    id-E-RABs-ToBeModified-ModReqItem,
    id-E-RABs-ToBeReleased-ModReqItem,
    id-E-RABs-Admitted-ToBeAdded-ModAckList,
    id-E-RABs-Admitted-ToBeModified-ModAckList,
    id-E-RABs-Admitted-ToBeReleased-ModAckList,
    id-E-RABs-Admitted-ToBeAdded-ModAckItem,
    id-E-RABs-Admitted-ToBeModified-ModAckItem,
    id-E-RABs-Admitted-ToBeReleased-ModAckItem,
    id-SCGChangeIndication,
    id-E-RABs-ToBeReleased-ModReqd,
    id-E-RABs-ToBeReleased-ModReqdItem,
    id-E-RABs-ToBeReleased-List-RelReq,
    id-E-RABs-ToBeReleased-RelReqItem,
    id-E-RABs-ToBeReleased-List-RelConf,
    id-E-RABs-ToBeReleased-RelConfItem,
    id-E-RABs-SubjectToCounterCheck-List,
    id-E-RABs-SubjectToCounterCheckItem,
    id-CoMPInformation,
    id-ReportingPeriodicityRSRPMR,
    id-RSRPMRList,
    id-UE-RLF-Report-Container-for-extended-bands,

    maxCellineNB,
    maxnoofBearers,
    maxnoofPDCP-SN,
    maxFailedMeasObjects,
    maxnoofCellIDforMDT,
    maxnoofTAforMDT
FROM X2AP-Constants;

-- **************************************************************
--
-- HANDOVER REQUEST
--
-- **************************************************************

HandoverRequest ::= SEQUENCE {
    protocolIEs         ProtocolIE-Container    {{HandoverRequest-IEs}},
    ...
}

HandoverRequest-IEs X2AP-PROTOCOL-IES ::= {
    { ID id-Old-eNB-UE-X2AP-ID              CRITICALITY reject  TYPE UE-X2AP-ID                         PRESENCE mandatory}|
    { ID id-Cause                           CRITICALITY ignore  TYPE Cause                              PRESENCE mandatory}|
    { ID id-TargetCell-ID                   CRITICALITY reject  TYPE ECGI                               PRESENCE mandatory}|
    { ID id-GUMMEI-ID                       CRITICALITY reject  TYPE GUMMEI                             PRESENCE mandatory}|
    { ID id-UE-ContextInformation           CRITICALITY reject  TYPE UE-ContextInformation              PRESENCE mandatory}|
    { ID id-UE-HistoryInformation           CRITICALITY ignore  TYPE UE-HistoryInformation              PRESENCE mandatory}|
    { ID id-TraceActivation                 CRITICALITY ignore  TYPE TraceActivation                    PRESENCE optional}|
    { ID id-SRVCCOperationPossible          CRITICALITY ignore  TYPE SRVCCOperationPossible             PRESENCE optional}|
    { ID id-CSGMembershipStatus             CRITICALITY reject  TYPE CSGMembershipStatus                PRESENCE optional}|
    { ID id-MobilityInformation             CRITICALITY ignore  TYPE MobilityInformation                PRESENCE optional}|
    { ID id-Masked-IMEISV                   CRITICALITY ignore  TYPE Masked-IMEISV                      PRESENCE optional}|
    { ID id-UE-HistoryInformationFromTheUE  CRITICALITY ignore  TYPE UE-HistoryInformationFromTheUE PRESENCE optional}|
    { ID id-ExpectedUEBehaviour             CRITICALITY ignore  TYPE ExpectedUEBehaviour                PRESENCE optional},
    ...
}

UE-ContextInformation ::= SEQUENCE {
    mME-UE-S1AP-ID                      UE-S1AP-ID,
    uESecurityCapabilities              UESecurityCapabilities,
    aS-SecurityInformation              AS-SecurityInformation,
    uEaggregateMaximumBitRate           UEAggregateMaximumBitRate,
    subscriberProfileIDforRFP           SubscriberProfileIDforRFP       OPTIONAL,
    e-RABs-ToBeSetup-List               E-RABs-ToBeSetup-List,
    rRC-Context                         RRC-Context,
    handoverRestrictionList             HandoverRestrictionList     OPTIONAL,
    locationReportingInformation        LocationReportingInformation    OPTIONAL,
    iE-Extensions                       ProtocolExtensionContainer { {UE-ContextInformation-ExtIEs} } OPTIONAL,
    ...
}

UE-ContextInformation-ExtIEs X2AP-PROTOCOL-EXTENSION ::= {
{ ID id-ManagementBasedMDTallowed   CRITICALITY ignore  EXTENSION ManagementBasedMDTallowed     PRESENCE optional }|
{ ID id-ManagementBasedMDTPLMNList  CRITICALITY ignore  EXTENSION MDTPLMNList                   PRESENCE optional },
    ...
}

E-RABs-ToBeSetup-List ::= SEQUENCE (SIZE(1..maxnoofBearers)) OF ProtocolIE-Single-Container { {E-RABs-ToBeSetup-ItemIEs} }

E-RABs-ToBeSetup-ItemIEs    X2AP-PROTOCOL-IES ::= {
    { ID id-E-RABs-ToBeSetup-Item    CRITICALITY ignore     TYPE E-RABs-ToBeSetup-Item  PRESENCE mandatory },
    ...
}

E-RABs-ToBeSetup-Item ::= SEQUENCE {
    e-RAB-ID                    E-RAB-ID,
    e-RAB-Level-QoS-Parameters      E-RAB-Level-QoS-Parameters,
    dL-Forwarding                   DL-Forwarding                                                   OPTIONAL,
    uL-GTPtunnelEndpoint            GTPtunnelEndpoint,
    iE-Extensions                   ProtocolExtensionContainer { {E-RABs-ToBeSetup-ItemExtIEs} } OPTIONAL,
    ...
}

E-RABs-ToBeSetup-ItemExtIEs X2AP-PROTOCOL-EXTENSION ::= {
    ...
}

MobilityInformation ::= BIT STRING (SIZE(32))

-- **************************************************************
--
-- HANDOVER REQUEST ACKNOWLEDGE
--
-- **************************************************************

HandoverRequestAcknowledge ::= SEQUENCE {
    protocolIEs     ProtocolIE-Container    {{HandoverRequestAcknowledge-IEs}},
    ...
}

HandoverRequestAcknowledge-IEs X2AP-PROTOCOL-IES ::= {
    { ID id-Old-eNB-UE-X2AP-ID                          CRITICALITY ignore  TYPE UE-X2AP-ID     PRESENCE mandatory} |
    { ID id-New-eNB-UE-X2AP-ID                          CRITICALITY ignore  TYPE UE-X2AP-ID     PRESENCE mandatory} |
    { ID id-E-RABs-Admitted-List                        CRITICALITY ignore  TYPE E-RABs-Admitted-List   PRESENCE mandatory} |
    { ID id-E-RABs-NotAdmitted-List                     CRITICALITY ignore  TYPE E-RAB-List     PRESENCE optional} |
    { ID id-TargeteNBtoSource-eNBTransparentContainer   CRITICALITY ignore  TYPE TargeteNBtoSource-eNBTransparentContainer  PRESENCE mandatory }|
    { ID id-CriticalityDiagnostics                      CRITICALITY ignore  TYPE CriticalityDiagnostics PRESENCE optional },
    ...
}

E-RABs-Admitted-List        ::= SEQUENCE (SIZE (1..maxnoofBearers)) OF ProtocolIE-Single-Container { {E-RABs-Admitted-ItemIEs} }

E-RABs-Admitted-ItemIEs X2AP-PROTOCOL-IES ::= {
    { ID id-E-RABs-Admitted-Item    CRITICALITY ignore  TYPE E-RABs-Admitted-Item   PRESENCE mandatory  }
}

E-RABs-Admitted-Item ::= SEQUENCE {
    e-RAB-ID                    E-RAB-ID,
    uL-GTP-TunnelEndpoint           GTPtunnelEndpoint   OPTIONAL,
    dL-GTP-TunnelEndpoint           GTPtunnelEndpoint   OPTIONAL,
    iE-Extensions                   ProtocolExtensionContainer { {E-RABs-Admitted-Item-ExtIEs} }    OPTIONAL,
    ...
}

E-RABs-Admitted-Item-ExtIEs X2AP-PROTOCOL-EXTENSION ::= {
    ...
}

-- **************************************************************
--
-- HANDOVER PREPARATION FAILURE
--
-- **************************************************************

HandoverPreparationFailure ::= SEQUENCE {
    protocolIEs     ProtocolIE-Container    {{HandoverPreparationFailure-IEs}},
    ...
}

HandoverPreparationFailure-IEs X2AP-PROTOCOL-IES ::= {
    { ID id-Old-eNB-UE-X2AP-ID          CRITICALITY ignore  TYPE UE-X2AP-ID             PRESENCE mandatory} |
    { ID id-Cause                       CRITICALITY ignore  TYPE Cause                  PRESENCE mandatory} |
    { ID id-CriticalityDiagnostics      CRITICALITY ignore  TYPE CriticalityDiagnostics PRESENCE optional },

    ...
}

-- **************************************************************
--
-- Handover Report
--
-- **************************************************************

HandoverReport ::= SEQUENCE {
    protocolIEs     ProtocolIE-Container    {{HandoverReport-IEs}},
    ...
}

HandoverReport-IEs X2AP-PROTOCOL-IES ::= {
    { ID id-HandoverReportType                          CRITICALITY ignore  TYPE HandoverReportType                                 PRESENCE mandatory}|
    { ID id-Cause                                       CRITICALITY ignore  TYPE Cause                                                  PRESENCE mandatory}|
    { ID id-SourceCellECGI                              CRITICALITY ignore  TYPE ECGI                                                   PRESENCE mandatory}|
    { ID id-FailureCellECGI                             CRITICALITY ignore  TYPE ECGI                                                   PRESENCE mandatory}|
    { ID id-Re-establishmentCellECGI                    CRITICALITY ignore  TYPE ECGI                                                   PRESENCE conditional} -- The IE shall be present if the Handover Report Type IE is set to “HO to Wrong Cell” -- |
    { ID id-TargetCellInUTRAN                           CRITICALITY ignore  TYPE TargetCellInUTRAN                                  PRESENCE conditional} -- The IE shall be present if the Handover Report Type IE is set to "InterRAT ping-pong" --|
    { ID id-SourceCellCRNTI                             CRITICALITY ignore  TYPE CRNTI                                                  PRESENCE optional}|
    { ID id-MobilityInformation                         CRITICALITY ignore  TYPE MobilityInformation                                    PRESENCE optional}|
    { ID id-UE-RLF-Report-Container                     CRITICALITY ignore  TYPE UE-RLF-Report-Container                            PRESENCE optional}|
    { ID id-UE-RLF-Report-Container-for-extended-bands  CRITICALITY ignore  TYPE UE-RLF-Report-Container-for-extended-bands PRESENCE optional},
    ...
}

-- **************************************************************
--
-- SN Status Transfer
--
-- **************************************************************

SNStatusTransfer ::= SEQUENCE {
    protocolIEs     ProtocolIE-Container    {{SNStatusTransfer-IEs}},
    ...
}

SNStatusTransfer-IEs X2AP-PROTOCOL-IES ::= {
    { ID id-Old-eNB-UE-X2AP-ID                      CRITICALITY reject  TYPE UE-X2AP-ID                     PRESENCE mandatory} |
    { ID id-New-eNB-UE-X2AP-ID                      CRITICALITY reject  TYPE UE-X2AP-ID                     PRESENCE mandatory} |
    { ID id-E-RABs-SubjectToStatusTransfer-List CRITICALITY ignore  TYPE E-RABs-SubjectToStatusTransfer-List    PRESENCE mandatory} ,
    ...
}

E-RABs-SubjectToStatusTransfer-List ::= SEQUENCE (SIZE (1..maxnoofBearers)) OF ProtocolIE-Single-Container { { E-RABs-SubjectToStatusTransfer-ItemIEs} }

E-RABs-SubjectToStatusTransfer-ItemIEs X2AP-PROTOCOL-IES ::= {
    { ID id-E-RABs-SubjectToStatusTransfer-Item CRITICALITY ignore  TYPE E-RABs-SubjectToStatusTransfer-Item    PRESENCE mandatory  }
}

E-RABs-SubjectToStatusTransfer-Item ::= SEQUENCE {
    e-RAB-ID                                E-RAB-ID,
    
    receiveStatusofULPDCPSDUs               ReceiveStatusofULPDCPSDUs           OPTIONAL,
    uL-COUNTvalue                   COUNTvalue,
    dL-COUNTvalue                   COUNTvalue,
    iE-Extensions                           ProtocolExtensionContainer { {E-RABs-SubjectToStatusTransfer-ItemExtIEs} } OPTIONAL,
    ...
}

E-RABs-SubjectToStatusTransfer-ItemExtIEs X2AP-PROTOCOL-EXTENSION ::= {
    { ID id-ReceiveStatusOfULPDCPSDUsExtended   CRITICALITY ignore  EXTENSION ReceiveStatusOfULPDCPSDUsExtended     PRESENCE optional}|
    { ID id-ULCOUNTValueExtended                CRITICALITY ignore  EXTENSION COUNTValueExtended                            PRESENCE optional}|
    { ID id-DLCOUNTValueExtended                CRITICALITY ignore  EXTENSION COUNTValueExtended                            PRESENCE optional},
    ...
}

-- **************************************************************
--
-- UE Context Release 
--
-- **************************************************************

UEContextRelease ::= SEQUENCE {
    protocolIEs     ProtocolIE-Container    {{UEContextRelease-IEs}},
    ...
}

UEContextRelease-IEs X2AP-PROTOCOL-IES ::= {
    { ID id-Old-eNB-UE-X2AP-ID          CRITICALITY reject  TYPE UE-X2AP-ID             PRESENCE mandatory} |
    { ID id-New-eNB-UE-X2AP-ID          CRITICALITY reject  TYPE UE-X2AP-ID             PRESENCE mandatory} ,
    ...
}


-- **************************************************************
--
-- HANDOVER CANCEL
--
-- **************************************************************

HandoverCancel ::= SEQUENCE {
    protocolIEs     ProtocolIE-Container    {{HandoverCancel-IEs}},
    ...
}

HandoverCancel-IEs X2AP-PROTOCOL-IES ::= {
    { ID id-Old-eNB-UE-X2AP-ID          CRITICALITY reject  TYPE UE-X2AP-ID             PRESENCE mandatory} |
    { ID id-New-eNB-UE-X2AP-ID          CRITICALITY ignore  TYPE UE-X2AP-ID             PRESENCE optional} |
    { ID id-Cause                       CRITICALITY ignore  TYPE Cause                  PRESENCE mandatory} ,
    ...
}

-- **************************************************************
--
-- ERROR INDICATION
--
-- **************************************************************

ErrorIndication ::= SEQUENCE {
    protocolIEs     ProtocolIE-Container    {{ErrorIndication-IEs}},
    ...
}

ErrorIndication-IEs X2AP-PROTOCOL-IES ::= {
    { ID id-Old-eNB-UE-X2AP-ID          CRITICALITY ignore  TYPE UE-X2AP-ID                 PRESENCE optional} |
    { ID id-New-eNB-UE-X2AP-ID          CRITICALITY ignore  TYPE UE-X2AP-ID                 PRESENCE optional} |
    { ID id-Cause                       CRITICALITY ignore  TYPE Cause                      PRESENCE optional} |
    { ID id-CriticalityDiagnostics      CRITICALITY ignore  TYPE CriticalityDiagnostics     PRESENCE optional} ,
    ...
}

-- **************************************************************
--
-- Reset Request
--
-- **************************************************************

ResetRequest ::= SEQUENCE {
    protocolIEs     ProtocolIE-Container    {{ResetRequest-IEs}},
    ...
}

ResetRequest-IEs X2AP-PROTOCOL-IES ::= {
    { ID id-Cause               CRITICALITY ignore  TYPE Cause              PRESENCE mandatory},
    ...
}

-- **************************************************************
--
-- Reset Response
--
-- **************************************************************

ResetResponse ::= SEQUENCE {
    protocolIEs     ProtocolIE-Container    {{ResetResponse-IEs}},
    ...
}

ResetResponse-IEs X2AP-PROTOCOL-IES ::= {
    { ID id-CriticalityDiagnostics  CRITICALITY ignore  TYPE CriticalityDiagnostics         PRESENCE optional },
    ...
}

-- **************************************************************
--
-- X2 SETUP REQUEST
--
-- **************************************************************

X2SetupRequest ::= SEQUENCE {
    protocolIEs     ProtocolIE-Container    {{X2SetupRequest-IEs}},
    ...
}

X2SetupRequest-IEs X2AP-PROTOCOL-IES ::= {
    { ID id-GlobalENB-ID                CRITICALITY reject  TYPE GlobalENB-ID               PRESENCE mandatory} |
    { ID id-ServedCells                     CRITICALITY reject  TYPE ServedCells            PRESENCE mandatory} |
    { ID id-GUGroupIDList                   CRITICALITY reject  TYPE GUGroupIDList          PRESENCE optional},
...
}



-- **************************************************************
--
-- X2 SETUP RESPONSE
--
-- **************************************************************

X2SetupResponse ::= SEQUENCE {
    protocolIEs     ProtocolIE-Container    {{X2SetupResponse-IEs}},
    ...
}

X2SetupResponse-IEs X2AP-PROTOCOL-IES ::= {
    { ID id-GlobalENB-ID                    CRITICALITY reject  TYPE GlobalENB-ID           PRESENCE mandatory} |
    { ID id-ServedCells                     CRITICALITY reject  TYPE ServedCells            PRESENCE mandatory} |
    { ID id-GUGroupIDList                   CRITICALITY reject  TYPE GUGroupIDList          PRESENCE optional}|
    { ID id-CriticalityDiagnostics          CRITICALITY ignore  TYPE CriticalityDiagnostics PRESENCE optional },
    ...
}



-- **************************************************************
--
-- X2 SETUP FAILURE
--
-- **************************************************************

X2SetupFailure ::= SEQUENCE {
    protocolIEs     ProtocolIE-Container    {{X2SetupFailure-IEs}},
    ...
}

X2SetupFailure-IEs X2AP-PROTOCOL-IES ::= {
    { ID id-Cause                   CRITICALITY ignore      TYPE Cause                              PRESENCE mandatory} |
    { ID id-TimeToWait              CRITICALITY ignore      TYPE TimeToWait                         PRESENCE optional} |
    { ID id-CriticalityDiagnostics  CRITICALITY ignore      TYPE CriticalityDiagnostics             PRESENCE optional },

    ...
}



-- **************************************************************
--
-- LOAD INFORMATION
--
-- **************************************************************

LoadInformation ::= SEQUENCE {
    protocolIEs     ProtocolIE-Container    {{LoadInformation-IEs}},
    ...
}

LoadInformation-IEs X2AP-PROTOCOL-IES ::= {
    { ID id-CellInformation             CRITICALITY ignore  TYPE CellInformation-List       PRESENCE mandatory} ,
    ...
}

CellInformation-List ::= SEQUENCE (SIZE (1..maxCellineNB)) OF ProtocolIE-Single-Container { {CellInformation-ItemIEs} }

CellInformation-ItemIEs X2AP-PROTOCOL-IES ::= {
    { ID id-CellInformation-Item    CRITICALITY ignore  TYPE CellInformation-Item   PRESENCE mandatory  }
}

CellInformation-Item ::= SEQUENCE {
    cell-ID                         ECGI,
    ul-InterferenceOverloadIndication       UL-InterferenceOverloadIndication       OPTIONAL,
    ul-HighInterferenceIndicationInfo       UL-HighInterferenceIndicationInfo       OPTIONAL,
    relativeNarrowbandTxPower               RelativeNarrowbandTxPower               OPTIONAL,
    iE-Extensions                           ProtocolExtensionContainer { {CellInformation-Item-ExtIEs} }    OPTIONAL,
    ...
}

CellInformation-Item-ExtIEs X2AP-PROTOCOL-EXTENSION ::= {
{ ID id-ABSInformation                      CRITICALITY ignore  EXTENSION ABSInformation                            PRESENCE optional }|
{ ID id-InvokeIndication                    CRITICALITY ignore  EXTENSION InvokeIndication                          PRESENCE optional }|
{ ID id-IntendedULDLConfiguration           CRITICALITY ignore  EXTENSION SubframeAssignment                        PRESENCE optional }|
{ ID id-ExtendedULInterferenceOverloadInfo  CRITICALITY ignore  EXTENSION ExtendedULInterferenceOverloadInfo    PRESENCE optional }|
{ ID id-CoMPInformation                     CRITICALITY ignore  EXTENSION CoMPInformation                           PRESENCE optional }|
{ ID id-DynamicDLTransmissionInformation    CRITICALITY ignore  EXTENSION DynamicDLTransmissionInformation      PRESENCE optional },
    ...
}

-- **************************************************************
--
-- ENB CONFIGURATION UPDATE
--
-- **************************************************************

ENBConfigurationUpdate ::= SEQUENCE {
    protocolIEs     ProtocolIE-Container    {{ENBConfigurationUpdate-IEs}},
    ...
}

ENBConfigurationUpdate-IEs X2AP-PROTOCOL-IES ::= {
    { ID id-ServedCellsToAdd        CRITICALITY reject  TYPE ServedCells                PRESENCE optional}|
    { ID id-ServedCellsToModify     CRITICALITY reject  TYPE ServedCellsToModify        PRESENCE optional}|
    { ID id-ServedCellsToDelete     CRITICALITY reject  TYPE Old-ECGIs                  PRESENCE optional}|
    { ID id-GUGroupIDToAddList      CRITICALITY reject  TYPE GUGroupIDList              PRESENCE optional}|
    { ID id-GUGroupIDToDeleteList   CRITICALITY reject  TYPE GUGroupIDList              PRESENCE optional},
    ...
}

ServedCellsToModify::= SEQUENCE (SIZE (1..maxCellineNB)) OF ServedCellsToModify-Item
 
ServedCellsToModify-Item::= SEQUENCE {
    old-ecgi                        ECGI,
    servedCellInfo                  ServedCell-Information,
    neighbour-Info                  Neighbour-Information           OPTIONAL,
    iE-Extensions                   ProtocolExtensionContainer { { ServedCellsToModify-Item-ExtIEs} } OPTIONAL,
    ...
}

ServedCellsToModify-Item-ExtIEs X2AP-PROTOCOL-EXTENSION ::= {
{ ID id-DeactivationIndication          CRITICALITY ignore  EXTENSION DeactivationIndication                PRESENCE optional },
    ...
}


Old-ECGIs::= SEQUENCE (SIZE (1..maxCellineNB)) OF ECGI

-- **************************************************************
--
-- ENB CONFIGURATION UPDATE ACKNOWLEDGE
--
-- **************************************************************

ENBConfigurationUpdateAcknowledge ::= SEQUENCE {
    protocolIEs     ProtocolIE-Container    {{ENBConfigurationUpdateAcknowledge-IEs}},
    ...
}

ENBConfigurationUpdateAcknowledge-IEs X2AP-PROTOCOL-IES ::= {
    { ID id-CriticalityDiagnostics      CRITICALITY ignore  TYPE CriticalityDiagnostics         PRESENCE optional},
...
}

-- **************************************************************
--
-- ENB CONFIGURATION UPDATE FAIURE
--
-- **************************************************************

ENBConfigurationUpdateFailure ::= SEQUENCE {
    protocolIEs     ProtocolIE-Container    {{ENBConfigurationUpdateFailure-IEs}},
    ...
}

ENBConfigurationUpdateFailure-IEs X2AP-PROTOCOL-IES ::= {
    { ID id-Cause                       CRITICALITY ignore  TYPE Cause                      PRESENCE mandatory}|
    { ID id-TimeToWait                  CRITICALITY ignore  TYPE TimeToWait                 PRESENCE optional}|
    { ID id-CriticalityDiagnostics      CRITICALITY ignore  TYPE CriticalityDiagnostics     PRESENCE optional},
    ...
}



-- **************************************************************
--
-- Resource Status Request
--
-- **************************************************************

ResourceStatusRequest ::= SEQUENCE {
    protocolIEs     ProtocolIE-Container    {{ResourceStatusRequest-IEs}},
    ...
}

ResourceStatusRequest-IEs X2AP-PROTOCOL-IES ::= {
    { ID id-ENB1-Measurement-ID         CRITICALITY reject  TYPE Measurement-ID                 PRESENCE mandatory}|
    { ID id-ENB2-Measurement-ID         CRITICALITY ignore  TYPE Measurement-ID                 PRESENCE conditional}|-- The IE shall be present if the Registration Request IE is set to “Stop”--
    { ID id-Registration-Request        CRITICALITY reject  TYPE Registration-Request           PRESENCE mandatory}|
    { ID id-ReportCharacteristics       CRITICALITY reject  TYPE ReportCharacteristics          PRESENCE optional}|
    { ID id-CellToReport                CRITICALITY ignore  TYPE CellToReport-List              PRESENCE mandatory}|
    { ID id-ReportingPeriodicity        CRITICALITY ignore  TYPE ReportingPeriodicity           PRESENCE optional}|
    { ID id-PartialSuccessIndicator     CRITICALITY ignore  TYPE PartialSuccessIndicator        PRESENCE optional}|
    { ID id-ReportingPeriodicityRSRPMR  CRITICALITY ignore  TYPE ReportingPeriodicityRSRPMR     PRESENCE optional},
    ...
}


CellToReport-List       ::= SEQUENCE (SIZE (1..maxCellineNB)) OF ProtocolIE-Single-Container { {CellToReport-ItemIEs} }

CellToReport-ItemIEs X2AP-PROTOCOL-IES ::= {
    { ID id-CellToReport-Item   CRITICALITY ignore  TYPE CellToReport-Item  PRESENCE mandatory}
}

CellToReport-Item ::= SEQUENCE {
    cell-ID                                 ECGI,
    iE-Extensions                           ProtocolExtensionContainer { {CellToReport-Item-ExtIEs} } OPTIONAL,
    ...
}

CellToReport-Item-ExtIEs X2AP-PROTOCOL-EXTENSION ::= {
    ...
}


ReportingPeriodicity ::= ENUMERATED {
    one-thousand-ms,
    two-thousand-ms,
    five-thousand-ms,
    ten-thousand-ms,
...
}

PartialSuccessIndicator ::= ENUMERATED {
    partial-success-allowed,
...
}

-- **************************************************************
--
-- Resource Status Response
--
-- **************************************************************

ResourceStatusResponse ::= SEQUENCE {
    protocolIEs     ProtocolIE-Container    {{ResourceStatusResponse-IEs}},
    ...
}

ResourceStatusResponse-IEs X2AP-PROTOCOL-IES ::= {
    { ID id-ENB1-Measurement-ID                 CRITICALITY reject  TYPE Measurement-ID                         PRESENCE mandatory}|
    { ID id-ENB2-Measurement-ID                 CRITICALITY reject  TYPE Measurement-ID                         PRESENCE mandatory}|
    { ID id-CriticalityDiagnostics              CRITICALITY ignore  TYPE CriticalityDiagnostics                 PRESENCE optional}|
    { ID id-MeasurementInitiationResult-List    CRITICALITY ignore  TYPE MeasurementInitiationResult-List   PRESENCE optional},
    ...
}


MeasurementInitiationResult-List ::= SEQUENCE (SIZE (1..maxCellineNB)) OF ProtocolIE-Single-Container { { MeasurementInitiationResult-ItemIEs} }

MeasurementInitiationResult-ItemIEs X2AP-PROTOCOL-IES ::= {
    { ID id-MeasurementInitiationResult-Item    CRITICALITY ignore  TYPE MeasurementInitiationResult-Item   PRESENCE mandatory}
}

MeasurementInitiationResult-Item ::= SEQUENCE {
    cell-ID                                         ECGI,
    measurementFailureCause-List                    MeasurementFailureCause-List    OPTIONAL,
    iE-Extensions                                   ProtocolExtensionContainer { { MeasurementInitiationResult-Item-ExtIEs} }   OPTIONAL,
    ...
}

MeasurementInitiationResult-Item-ExtIEs X2AP-PROTOCOL-EXTENSION ::= {
    ...
}

MeasurementFailureCause-List ::= SEQUENCE (SIZE (1..maxFailedMeasObjects)) OF ProtocolIE-Single-Container { { MeasurementFailureCause-ItemIEs} }

MeasurementFailureCause-ItemIEs X2AP-PROTOCOL-IES ::= {
    { ID id-MeasurementFailureCause-Item    CRITICALITY ignore  TYPE MeasurementFailureCause-Item       PRESENCE mandatory}
}

MeasurementFailureCause-Item ::= SEQUENCE {
    measurementFailedReportCharacteristics          ReportCharacteristics,
    cause                                           Cause,
    iE-Extensions                                   ProtocolExtensionContainer { { MeasurementFailureCause-Item-ExtIEs} }   OPTIONAL,
    ...
}

MeasurementFailureCause-Item-ExtIEs X2AP-PROTOCOL-EXTENSION ::= {
    ...
}

-- **************************************************************
--
-- Resource Status Failure
--
-- **************************************************************

ResourceStatusFailure ::= SEQUENCE {
    protocolIEs     ProtocolIE-Container    {{ResourceStatusFailure-IEs}},
    ...
}

ResourceStatusFailure-IEs X2AP-PROTOCOL-IES ::= {
    { ID id-ENB1-Measurement-ID                     CRITICALITY reject  TYPE Measurement-ID                                 PRESENCE mandatory}|
    { ID id-ENB2-Measurement-ID                     CRITICALITY reject  TYPE Measurement-ID                                 PRESENCE mandatory}|
    { ID id-Cause                                   CRITICALITY ignore  TYPE Cause                                          PRESENCE mandatory}|
    { ID id-CriticalityDiagnostics                  CRITICALITY ignore  TYPE CriticalityDiagnostics                     PRESENCE optional}|
    { ID id-CompleteFailureCauseInformation-List    CRITICALITY ignore  TYPE CompleteFailureCauseInformation-List   PRESENCE optional},
    ...
}

CompleteFailureCauseInformation-List ::= SEQUENCE (SIZE (1..maxCellineNB)) OF ProtocolIE-Single-Container { {CompleteFailureCauseInformation-ItemIEs} }

CompleteFailureCauseInformation-ItemIEs X2AP-PROTOCOL-IES ::= {
    { ID id-CompleteFailureCauseInformation-Item    CRITICALITY ignore  TYPE CompleteFailureCauseInformation-Item   PRESENCE mandatory}
}

CompleteFailureCauseInformation-Item ::= SEQUENCE {
    cell-ID                                         ECGI,
    measurementFailureCause-List                    MeasurementFailureCause-List,
    iE-Extensions                                   ProtocolExtensionContainer { { CompleteFailureCauseInformation-Item-ExtIEs} }   OPTIONAL,
    ...
}

CompleteFailureCauseInformation-Item-ExtIEs X2AP-PROTOCOL-EXTENSION ::= {
    ...
}

-- **************************************************************
--
-- Resource Status Update
--
-- **************************************************************

ResourceStatusUpdate ::= SEQUENCE {
    protocolIEs     ProtocolIE-Container    {{ResourceStatusUpdate-IEs}},
    ...
}

ResourceStatusUpdate-IEs X2AP-PROTOCOL-IES ::= {
    { ID id-ENB1-Measurement-ID     CRITICALITY reject  TYPE Measurement-ID                 PRESENCE mandatory}|
    { ID id-ENB2-Measurement-ID     CRITICALITY reject  TYPE Measurement-ID                 PRESENCE mandatory}|
    { ID id-CellMeasurementResult   CRITICALITY ignore  TYPE CellMeasurementResult-List     PRESENCE mandatory},
    ...
}

CellMeasurementResult-List ::= SEQUENCE (SIZE (1..maxCellineNB)) OF ProtocolIE-Single-Container { {CellMeasurementResult-ItemIEs} }

CellMeasurementResult-ItemIEs X2AP-PROTOCOL-IES ::= {
    { ID id-CellMeasurementResult-Item  CRITICALITY ignore  TYPE CellMeasurementResult-Item PRESENCE mandatory}
}

CellMeasurementResult-Item ::= SEQUENCE {
    cell-ID                     ECGI,
    hWLoadIndicator             HWLoadIndicator     OPTIONAL,
    s1TNLLoadIndicator          S1TNLLoadIndicator  OPTIONAL,
    radioResourceStatus         RadioResourceStatus OPTIONAL,
    iE-Extensions               ProtocolExtensionContainer { {CellMeasurementResult-Item-ExtIEs} }  OPTIONAL,
    ...
}

CellMeasurementResult-Item-ExtIEs X2AP-PROTOCOL-EXTENSION ::= {
    { ID id-CompositeAvailableCapacityGroup CRITICALITY ignore  EXTENSION CompositeAvailableCapacityGroup       PRESENCE optional}|
    { ID id-ABS-Status                      CRITICALITY ignore  EXTENSION ABS-Status                                PRESENCE optional}|
    { ID id-RSRPMRList                      CRITICALITY ignore  EXTENSION RSRPMRList                                PRESENCE optional},
    ...
}


-- **************************************************************
--
-- PRIVATE MESSAGE
--
-- **************************************************************

PrivateMessage ::= SEQUENCE {
    privateIEs      PrivateIE-Container {{PrivateMessage-IEs}},
    ...
}

PrivateMessage-IEs X2AP-PRIVATE-IES ::= {
    ...
}

-- **************************************************************
--
-- MOBILITY CHANGE REQUEST
--
-- **************************************************************

MobilityChangeRequest ::= SEQUENCE {
    protocolIEs     ProtocolIE-Container    {{MobilityChangeRequest-IEs}},
    ...
}

MobilityChangeRequest-IEs X2AP-PROTOCOL-IES ::= {
    { ID id-ENB1-Cell-ID                        CRITICALITY reject  TYPE ECGI                                           PRESENCE mandatory}|
    { ID id-ENB2-Cell-ID                        CRITICALITY reject  TYPE ECGI                                           PRESENCE mandatory}|
    { ID id-ENB1-Mobility-Parameters            CRITICALITY ignore  TYPE MobilityParametersInformation              PRESENCE optional}|
    { ID id-ENB2-Proposed-Mobility-Parameters   CRITICALITY reject  TYPE MobilityParametersInformation              PRESENCE mandatory}|
    { ID id-Cause                               CRITICALITY reject  TYPE Cause                                          PRESENCE mandatory},
    ...
}

-- **************************************************************
--
-- MOBILITY CHANGE ACKNOWLEDGE
--
-- **************************************************************

MobilityChangeAcknowledge ::= SEQUENCE {
    protocolIEs     ProtocolIE-Container    {{MobilityChangeAcknowledge-IEs}},
    ...
}

MobilityChangeAcknowledge-IEs X2AP-PROTOCOL-IES ::= {
    { ID id-ENB1-Cell-ID            CRITICALITY reject  TYPE ECGI                           PRESENCE mandatory}|
    { ID id-ENB2-Cell-ID            CRITICALITY reject  TYPE ECGI                           PRESENCE mandatory}|
    { ID id-CriticalityDiagnostics  CRITICALITY ignore  TYPE CriticalityDiagnostics         PRESENCE optional},
    ...
}


-- **************************************************************
--
-- MOBILITY CHANGE FAILURE
--
-- **************************************************************

MobilityChangeFailure ::= SEQUENCE {
    protocolIEs     ProtocolIE-Container    {{MobilityChangeFailure-IEs}},
    ...
}

MobilityChangeFailure-IEs X2AP-PROTOCOL-IES ::= {
    { ID id-ENB1-Cell-ID                                    CRITICALITY ignore  TYPE ECGI                                               PRESENCE mandatory}|
    { ID id-ENB2-Cell-ID                                    CRITICALITY ignore  TYPE ECGI                                               PRESENCE mandatory}|
    { ID id-Cause                                           CRITICALITY ignore  TYPE Cause                                              PRESENCE mandatory}|
    { ID id-ENB2-Mobility-Parameters-Modification-Range     CRITICALITY ignore  TYPE MobilityParametersModificationRange        PRESENCE optional}|
    { ID id-CriticalityDiagnostics                          CRITICALITY ignore  TYPE CriticalityDiagnostics                     PRESENCE optional},
    ...
}

-- **************************************************************
--
-- Radio Link Failure Indication
--
-- **************************************************************

RLFIndication ::= SEQUENCE {
    protocolIEs     ProtocolIE-Container    {{RLFIndication-IEs}},
    ...
}

RLFIndication-IEs X2AP-PROTOCOL-IES ::= {
    { ID id-FailureCellPCI                              CRITICALITY ignore  TYPE PCI                                                        PRESENCE mandatory}|
    { ID id-Re-establishmentCellECGI                    CRITICALITY ignore  TYPE ECGI                                                       PRESENCE mandatory}|
    { ID id-FailureCellCRNTI                            CRITICALITY ignore  TYPE CRNTI                                                      PRESENCE mandatory}|
    { ID id-ShortMAC-I                                  CRITICALITY ignore  TYPE ShortMAC-I                                                 PRESENCE optional}|
    { ID id-UE-RLF-Report-Container                     CRITICALITY ignore  TYPE UE-RLF-Report-Container                                PRESENCE optional}|
    { ID id-RRCConnSetupIndicator                       CRITICALITY reject  TYPE RRCConnSetupIndicator                                  PRESENCE optional}|
    { ID id-RRCConnReestabIndicator                     CRITICALITY ignore  TYPE RRCConnReestabIndicator                                PRESENCE optional}|
    { ID id-UE-RLF-Report-Container-for-extended-bands  CRITICALITY ignore  TYPE UE-RLF-Report-Container-for-extended-bands     PRESENCE optional},
    ...
}


-- **************************************************************
--
-- Cell Activation Request
--
-- **************************************************************

CellActivationRequest ::= SEQUENCE {
    protocolIEs     ProtocolIE-Container    {{CellActivationRequest-IEs}},
    ...
}

CellActivationRequest-IEs X2AP-PROTOCOL-IES ::= {
    { ID id-ServedCellsToActivate   CRITICALITY reject  TYPE ServedCellsToActivate      PRESENCE mandatory},
    ...
}

ServedCellsToActivate::= SEQUENCE (SIZE (1..maxCellineNB)) OF ServedCellsToActivate-Item
 
ServedCellsToActivate-Item::= SEQUENCE {
    ecgi                        ECGI,
    iE-Extensions                   ProtocolExtensionContainer { { ServedCellsToActivate-Item-ExtIEs} } OPTIONAL,
    ...
}

ServedCellsToActivate-Item-ExtIEs X2AP-PROTOCOL-EXTENSION ::= {
    ...
}

-- **************************************************************
--
-- Cell Activation Response
--
-- **************************************************************

CellActivationResponse ::= SEQUENCE {
    protocolIEs     ProtocolIE-Container    {{CellActivationResponse-IEs}},
    ...
}

CellActivationResponse-IEs X2AP-PROTOCOL-IES ::= {
    { ID id-ActivatedCellList       CRITICALITY ignore  TYPE ActivatedCellList              PRESENCE mandatory}|
    { ID id-CriticalityDiagnostics  CRITICALITY ignore  TYPE CriticalityDiagnostics         PRESENCE optional},
    ...
}

ActivatedCellList ::= SEQUENCE (SIZE (1..maxCellineNB)) OF ActivatedCellList-Item
 
ActivatedCellList-Item::= SEQUENCE {
    ecgi                                ECGI,
    iE-Extensions                       ProtocolExtensionContainer { { ActivatedCellList-Item-ExtIEs} } OPTIONAL,
    ...
}

ActivatedCellList-Item-ExtIEs X2AP-PROTOCOL-EXTENSION ::= {
    ...
}

--**************************************************************
--
-- CELL ACTIVATION FAILURE
--
-- **************************************************************

CellActivationFailure ::= SEQUENCE {
    protocolIEs     ProtocolIE-Container    {{CellActivationFailure-IEs}},
    ...
}

CellActivationFailure-IEs X2AP-PROTOCOL-IES ::= {
    { ID id-Cause                       CRITICALITY ignore  TYPE Cause                      PRESENCE mandatory }|
    { ID id-CriticalityDiagnostics      CRITICALITY ignore  TYPE CriticalityDiagnostics     PRESENCE optional },
    ...
}

-- **************************************************************
--
-- X2 RELEASE
--
-- **************************************************************

X2Release ::= SEQUENCE {
    protocolIEs     ProtocolIE-Container    {{X2Release-IEs}},
    ...
}

X2Release-IEs X2AP-PROTOCOL-IES ::= {
    { ID id-GlobalENB-ID            CRITICALITY reject  TYPE GlobalENB-ID           PRESENCE mandatory},
...
}

-- **************************************************************
--
-- X2 Message Transfer 
--
-- **************************************************************

X2MessageTransfer ::= SEQUENCE {
    protocolIEs     ProtocolIE-Container    {{X2MessageTransfer-IEs}},
    ...
}

X2MessageTransfer-IEs X2AP-PROTOCOL-IES ::= {
    { ID id-RNL-Header  CRITICALITY reject  TYPE RNL-Header             PRESENCE mandatory}|
    { ID id-x2APMessage CRITICALITY reject  TYPE X2AP-Message           PRESENCE optional},
    ...
}

RNL-Header ::= SEQUENCE {
    target-GlobalENB-ID GlobalENB-ID    OPTIONAL,
    source-GlobalENB-ID GlobalENB-ID,
    iE-Extensions                       ProtocolExtensionContainer { { RNL-Header-Item-ExtIEs} } OPTIONAL,
    ...
}

RNL-Header-Item-ExtIEs X2AP-PROTOCOL-EXTENSION ::= {
    ...
}

X2AP-Message ::= OCTET STRING

-- **************************************************************
--
-- SENB ADDITION REQUEST
--
-- **************************************************************

SeNBAdditionRequest ::= SEQUENCE {
    protocolIEs     ProtocolIE-Container    {{SeNBAdditionRequest-IEs}},
    ...
}

SeNBAdditionRequest-IEs X2AP-PROTOCOL-IES ::= {
    { ID id-MeNB-UE-X2AP-ID                 CRITICALITY reject  TYPE UE-X2AP-ID                         PRESENCE mandatory}|
    { ID id-UE-SecurityCapabilities         CRITICALITY reject  TYPE UESecurityCapabilities             PRESENCE conditional}|
    { ID id-SeNBSecurityKey                 CRITICALITY reject  TYPE SeNBSecurityKey                    PRESENCE conditional}|
    { ID id-UEAggregateMaximumBitRate       CRITICALITY reject  TYPE UEAggregateMaximumBitRate          PRESENCE mandatory}|
    { ID id-ServingPLMN                     CRITICALITY ignore  TYPE PLMN-Identity                      PRESENCE optional}|
    { ID id-E-RABs-ToBeAdded-List           CRITICALITY reject  TYPE E-RABs-ToBeAdded-List              PRESENCE mandatory}|
    { ID id-MeNBtoSeNBContainer             CRITICALITY reject  TYPE MeNBtoSeNBContainer                PRESENCE mandatory},
    ...
}

E-RABs-ToBeAdded-List ::= SEQUENCE (SIZE(1..maxnoofBearers)) OF ProtocolIE-Single-Container { { E-RABs-ToBeAdded-ItemIEs} }

E-RABs-ToBeAdded-ItemIEs X2AP-PROTOCOL-IES ::= {
    { ID id-E-RABs-ToBeAdded-Item   CRITICALITY ignore  TYPE E-RABs-ToBeAdded-Item      PRESENCE mandatory},
    ...
}

E-RABs-ToBeAdded-Item ::= CHOICE {
    sCG-Bearer      E-RABs-ToBeAdded-Item-SCG-Bearer,
    split-Bearer    E-RABs-ToBeAdded-Item-Split-Bearer,
    ...
}

E-RABs-ToBeAdded-Item-SCG-Bearer ::= SEQUENCE {
    e-RAB-ID                        E-RAB-ID,
    e-RAB-Level-QoS-Parameters      E-RAB-Level-QoS-Parameters,
    dL-Forwarding                   DL-Forwarding                                                                   OPTIONAL,
    s1-UL-GTPtunnelEndpoint         GTPtunnelEndpoint,
    iE-Extensions                   ProtocolExtensionContainer { {E-RABs-ToBeAdded-Item-SCG-BearerExtIEs} } OPTIONAL,
    ...
}

E-RABs-ToBeAdded-Item-SCG-BearerExtIEs X2AP-PROTOCOL-EXTENSION ::= {
    ...
}

E-RABs-ToBeAdded-Item-Split-Bearer ::= SEQUENCE {
    e-RAB-ID                        E-RAB-ID,
    e-RAB-Level-QoS-Parameters      E-RAB-Level-QoS-Parameters,
    meNB-GTPtunnelEndpoint          GTPtunnelEndpoint,
    iE-Extensions                   ProtocolExtensionContainer { {E-RABs-ToBeAdded-Item-Split-BearerExtIEs} } OPTIONAL,
    ...
}

E-RABs-ToBeAdded-Item-Split-BearerExtIEs X2AP-PROTOCOL-EXTENSION ::= {
    ...
}

-- **************************************************************
--
-- SENB ADDITION ACKNOWLEDGE
--
-- **************************************************************

SeNBAdditionAcknowledge ::= SEQUENCE {
    protocolIEs     ProtocolIE-Container    {{SeNBAdditionAcknowledge-IEs}},
    ...
}

SeNBAdditionAcknowledge-IEs X2AP-PROTOCOL-IES ::= {
    { ID id-MeNB-UE-X2AP-ID                     CRITICALITY reject  TYPE UE-X2AP-ID                         PRESENCE mandatory}|
    { ID id-SeNB-UE-X2AP-ID                     CRITICALITY reject  TYPE UE-X2AP-ID                         PRESENCE mandatory}|
    { ID id-E-RABs-Admitted-ToBeAdded-List      CRITICALITY ignore  TYPE E-RABs-Admitted-ToBeAdded-List PRESENCE mandatory}|
    { ID id-E-RABs-NotAdmitted-List             CRITICALITY ignore  TYPE E-RAB-List                         PRESENCE optional}|
    { ID id-SeNBtoMeNBContainer                 CRITICALITY reject  TYPE SeNBtoMeNBContainer                PRESENCE mandatory}|
    { ID id-CriticalityDiagnostics              CRITICALITY ignore  TYPE CriticalityDiagnostics             PRESENCE optional},
    ...
}

E-RABs-Admitted-ToBeAdded-List ::= SEQUENCE (SIZE (1..maxnoofBearers)) OF ProtocolIE-Single-Container { {E-RABs-Admitted-ToBeAdded-ItemIEs} }

E-RABs-Admitted-ToBeAdded-ItemIEs X2AP-PROTOCOL-IES ::= {
    { ID id-E-RABs-Admitted-ToBeAdded-Item  CRITICALITY ignore  TYPE E-RABs-Admitted-ToBeAdded-Item         PRESENCE mandatory}
}

E-RABs-Admitted-ToBeAdded-Item ::= CHOICE {
    sCG-Bearer      E-RABs-Admitted-ToBeAdded-Item-SCG-Bearer,
    split-Bearer    E-RABs-Admitted-ToBeAdded-Item-Split-Bearer,
    ...
}

E-RABs-Admitted-ToBeAdded-Item-SCG-Bearer ::= SEQUENCE {
    e-RAB-ID                                E-RAB-ID,
    s1-DL-GTPtunnelEndpoint                 GTPtunnelEndpoint,
    dL-Forwarding-GTPtunnelEndpoint         GTPtunnelEndpoint                                                                   OPTIONAL,
    uL-Forwarding-GTPtunnelEndpoint         GTPtunnelEndpoint                                                                   OPTIONAL,
    iE-Extensions                   ProtocolExtensionContainer { {E-RABs-Admitted-ToBeAdded-Item-SCG-BearerExtIEs} }    OPTIONAL,
    ...
}

E-RABs-Admitted-ToBeAdded-Item-SCG-BearerExtIEs X2AP-PROTOCOL-EXTENSION ::= {
    ...
}

E-RABs-Admitted-ToBeAdded-Item-Split-Bearer ::= SEQUENCE {
    e-RAB-ID                        E-RAB-ID,
    seNB-GTPtunnelEndpoint          GTPtunnelEndpoint,
    iE-Extensions                   ProtocolExtensionContainer { {E-RABs-Admitted-ToBeAdded-Item-Split-BearerExtIEs} } OPTIONAL,
    ...
}

E-RABs-Admitted-ToBeAdded-Item-Split-BearerExtIEs X2AP-PROTOCOL-EXTENSION ::= {
    ...
}

-- **************************************************************
--
-- SENB ADDITION REJECT
--
-- **************************************************************

SeNBAdditionReject ::= SEQUENCE {
    protocolIEs     ProtocolIE-Container    {{SeNBAdditionReject-IEs}},
    ...
}

SeNBAdditionReject-IEs X2AP-PROTOCOL-IES ::= {
    { ID id-MeNB-UE-X2AP-ID                 CRITICALITY reject  TYPE UE-X2AP-ID                 PRESENCE mandatory}|
    { ID id-SeNB-UE-X2AP-ID                 CRITICALITY reject  TYPE UE-X2AP-ID                 PRESENCE mandatory}|
    { ID id-Cause                           CRITICALITY ignore  TYPE Cause                      PRESENCE mandatory}|
    { ID id-CriticalityDiagnostics          CRITICALITY ignore  TYPE CriticalityDiagnostics     PRESENCE optional},
    ...
}

-- **************************************************************
--
-- SENB RECONFIGURATION COMPLETE
--
-- **************************************************************

SeNBReconfigurationComplete ::= SEQUENCE {
    protocolIEs     ProtocolIE-Container    {{SeNBReconfigurationComplete-IEs}},
    ...
}

SeNBReconfigurationComplete-IEs X2AP-PROTOCOL-IES ::= {
    { ID id-MeNB-UE-X2AP-ID                         CRITICALITY reject  TYPE UE-X2AP-ID                                 PRESENCE mandatory}|
    { ID id-SeNB-UE-X2AP-ID                         CRITICALITY reject  TYPE UE-X2AP-ID                                 PRESENCE mandatory}|
    { ID id-ResponseInformationSeNBReconfComp       CRITICALITY ignore  TYPE ResponseInformationSeNBReconfComp  PRESENCE mandatory},
    ...
}

ResponseInformationSeNBReconfComp ::= CHOICE {
    success             ResponseInformationSeNBReconfComp-SuccessItem,
    reject-by-MeNB      ResponseInformationSeNBReconfComp-RejectByMeNBItem,
    ...
}

ResponseInformationSeNBReconfComp-SuccessItem ::= SEQUENCE {
    meNBtoSeNBContainer             MeNBtoSeNBContainer OPTIONAL,
    iE-Extensions                   ProtocolExtensionContainer { {ResponseInformationSeNBReconfComp-SuccessItemExtIEs} }    OPTIONAL,
    ...
}

ResponseInformationSeNBReconfComp-SuccessItemExtIEs X2AP-PROTOCOL-EXTENSION ::= {
    ...
}

ResponseInformationSeNBReconfComp-RejectByMeNBItem ::= SEQUENCE {
    cause                           Cause,
    meNBtoSeNBContainer             MeNBtoSeNBContainer                                                                                     OPTIONAL,
    iE-Extensions                   ProtocolExtensionContainer { { ResponseInformationSeNBReconfComp-RejectByMeNBItemExtIEs} }  OPTIONAL,
    ...
}

ResponseInformationSeNBReconfComp-RejectByMeNBItemExtIEs X2AP-PROTOCOL-EXTENSION ::= {
    ...
}

-- **************************************************************
--
-- SENB MODIFICATION REQUEST
--
-- **************************************************************

SeNBModificationRequest ::= SEQUENCE {
    protocolIEs     ProtocolIE-Container    {{ SeNBModificationRequest-IEs}},
    ...
}

SeNBModificationRequest-IEs X2AP-PROTOCOL-IES ::= {
    { ID id-MeNB-UE-X2AP-ID             CRITICALITY reject  TYPE UE-X2AP-ID                 PRESENCE mandatory}|
    { ID id-SeNB-UE-X2AP-ID             CRITICALITY reject  TYPE UE-X2AP-ID                 PRESENCE mandatory}|
    { ID id-Cause                               CRITICALITY ignore  TYPE Cause                                  PRESENCE mandatory}|
    { ID id-SCGChangeIndication                 CRITICALITY ignore  TYPE SCGChangeIndication                    PRESENCE optional}|
    { ID id-ServingPLMN                         CRITICALITY ignore  TYPE PLMN-Identity                          PRESENCE optional}|
    { ID id-UE-ContextInformationSeNBModReq     CRITICALITY reject  TYPE UE-ContextInformationSeNBModReq    PRESENCE mandatory}|
    { ID id-MeNBtoSeNBContainer                 CRITICALITY ignore  TYPE MeNBtoSeNBContainer                    PRESENCE optional},
    ...
}

UE-ContextInformationSeNBModReq ::= SEQUENCE {
    uE-SecurityCapabilities         UESecurityCapabilities                                                          OPTIONAL,
    seNB-SecurityKey                SeNBSecurityKey                                                                 OPTIONAL,
    uEAggregateMaximumBitRate       UEAggregateMaximumBitRate                                                       OPTIONAL,
    e-RABs-ToBeAdded                E-RABs-ToBeAdded-List-ModReq                                                    OPTIONAL,
    e-RABs-ToBeModified             E-RABs-ToBeModified-List-ModReq                                                 OPTIONAL,
    e-RABs-ToBeReleased             E-RABs-ToBeReleased-List-ModReq                                                 OPTIONAL,
    iE-Extensions                   ProtocolExtensionContainer { { UE-ContextInformationSeNBModReqExtIEs} } OPTIONAL,
    ...
}

UE-ContextInformationSeNBModReqExtIEs X2AP-PROTOCOL-EXTENSION ::= {
    ...
}

E-RABs-ToBeAdded-List-ModReq ::= SEQUENCE (SIZE(1..maxnoofBearers)) OF ProtocolIE-Single-Container { {E-RABs-ToBeAdded-ModReqItemIEs} }

E-RABs-ToBeAdded-ModReqItemIEs X2AP-PROTOCOL-IES ::= {
    { ID id-E-RABs-ToBeAdded-ModReqItem CRITICALITY ignore  TYPE E-RABs-ToBeAdded-ModReqItem    PRESENCE mandatory},
    ...
}

E-RABs-ToBeAdded-ModReqItem ::= CHOICE {
    sCG-Bearer      E-RABs-ToBeAdded-ModReqItem-SCG-Bearer,
    split-Bearer    E-RABs-ToBeAdded-ModReqItem-Split-Bearer,
    ...
}

E-RABs-ToBeAdded-ModReqItem-SCG-Bearer ::= SEQUENCE {
    e-RAB-ID                        E-RAB-ID,
    e-RAB-Level-QoS-Parameters      E-RAB-Level-QoS-Parameters,
    dL-Forwarding                   DL-Forwarding                                                                   OPTIONAL,
    s1-UL-GTPtunnelEndpoint         GTPtunnelEndpoint,
    iE-Extensions                   ProtocolExtensionContainer { {E-RABs-ToBeAdded-ModReqItem-SCG-BearerExtIEs} } OPTIONAL,
    ...
}

E-RABs-ToBeAdded-ModReqItem-SCG-BearerExtIEs X2AP-PROTOCOL-EXTENSION ::= {
    ...
}

E-RABs-ToBeAdded-ModReqItem-Split-Bearer ::= SEQUENCE {
    e-RAB-ID                        E-RAB-ID,
    e-RAB-Level-QoS-Parameters      E-RAB-Level-QoS-Parameters,
    meNB-GTPtunnelEndpoint          GTPtunnelEndpoint,
    iE-Extensions           ProtocolExtensionContainer { {E-RABs-ToBeAdded-ModReqItem-Split-BearerExtIEs} } OPTIONAL,
    ...
}

E-RABs-ToBeAdded-ModReqItem-Split-BearerExtIEs X2AP-PROTOCOL-EXTENSION ::= {
    ...
}

E-RABs-ToBeModified-List-ModReq ::= SEQUENCE (SIZE(1..maxnoofBearers)) OF ProtocolIE-Single-Container { {E-RABs-ToBeModified-ModReqItemIEs} }

E-RABs-ToBeModified-ModReqItemIEs X2AP-PROTOCOL-IES ::= {
    { ID id-E-RABs-ToBeModified-ModReqItem  CRITICALITY ignore  TYPE E-RABs-ToBeModified-ModReqItem     PRESENCE mandatory},
    ...
}


E-RABs-ToBeModified-ModReqItem ::= CHOICE {
    sCG-Bearer      E-RABs-ToBeModified-ModReqItem-SCG-Bearer,
    split-Bearer    E-RABs-ToBeModified-ModReqItem-Split-Bearer,
    ...
}

E-RABs-ToBeModified-ModReqItem-SCG-Bearer ::= SEQUENCE {
    e-RAB-ID                        E-RAB-ID,
    e-RAB-Level-QoS-Parameters      E-RAB-Level-QoS-Parameters                                                      OPTIONAL,
    s1-UL-GTPtunnelEndpoint         GTPtunnelEndpoint                                                               OPTIONAL,
    iE-Extensions                   ProtocolExtensionContainer { {E-RABs-ToBeModified-ModReqItem-SCG-BearerExtIEs} } OPTIONAL,
    ...
}

E-RABs-ToBeModified-ModReqItem-SCG-BearerExtIEs X2AP-PROTOCOL-EXTENSION ::= {
    ...
}

E-RABs-ToBeModified-ModReqItem-Split-Bearer ::= SEQUENCE {
    e-RAB-ID                        E-RAB-ID,
    e-RAB-Level-QoS-Parameters      E-RAB-Level-QoS-Parameters                                                              OPTIONAL,
    meNB-GTPtunnelEndpoint          GTPtunnelEndpoint                                                                       OPTIONAL,
    iE-Extensions                   ProtocolExtensionContainer { {E-RABs-ToBeModified-ModReqItem-Split-BearerExtIEs} } OPTIONAL,
    ...
}

E-RABs-ToBeModified-ModReqItem-Split-BearerExtIEs X2AP-PROTOCOL-EXTENSION ::= {
    ...
}

E-RABs-ToBeReleased-List-ModReq ::= SEQUENCE (SIZE(1..maxnoofBearers)) OF ProtocolIE-Single-Container { {E-RABs-ToBeReleased-ModReqItemIEs} }

E-RABs-ToBeReleased-ModReqItemIEs X2AP-PROTOCOL-IES ::= {
    { ID id-E-RABs-ToBeReleased-ModReqItem  CRITICALITY ignore  TYPE E-RABs-ToBeReleased-ModReqItem     PRESENCE mandatory},
    ...
}

E-RABs-ToBeReleased-ModReqItem ::= CHOICE {
    sCG-Bearer      E-RABs-ToBeReleased-ModReqItem-SCG-Bearer,
    split-Bearer    E-RABs-ToBeReleased-ModReqItem-Split-Bearer,
    ...
}

E-RABs-ToBeReleased-ModReqItem-SCG-Bearer ::= SEQUENCE {
    e-RAB-ID                        E-RAB-ID,
    dL-GTPtunnelEndpoint            GTPtunnelEndpoint                                                               OPTIONAL,
    uL-GTPtunnelEndpoint            GTPtunnelEndpoint                                                               OPTIONAL,
    iE-Extensions                   ProtocolExtensionContainer { {E-RABs-ToBeReleased-ModReqItem-SCG-BearerExtIEs} } OPTIONAL,
    ...
}

E-RABs-ToBeReleased-ModReqItem-SCG-BearerExtIEs X2AP-PROTOCOL-EXTENSION ::= {
    ...
}

E-RABs-ToBeReleased-ModReqItem-Split-Bearer ::= SEQUENCE {
    e-RAB-ID                        E-RAB-ID, 
    dL-GTPtunnelEndpoint            GTPtunnelEndpoint                                                               OPTIONAL,
    iE-Extensions                   ProtocolExtensionContainer { {E-RABs-ToBeReleased-ModReqItem-Split-BearerExtIEs} } OPTIONAL,
    ...
}

E-RABs-ToBeReleased-ModReqItem-Split-BearerExtIEs X2AP-PROTOCOL-EXTENSION ::= {
    ...
}

-- **************************************************************
--
-- SENB MODIFICATION REQUEST ACKNOWLEDGE
--
-- **************************************************************

SeNBModificationRequestAcknowledge ::= SEQUENCE {
    protocolIEs     ProtocolIE-Container    {{SeNBModificationRequestAcknowledge-IEs}},
    ...
}

SeNBModificationRequestAcknowledge-IEs X2AP-PROTOCOL-IES ::= {
    { ID id-MeNB-UE-X2AP-ID                             CRITICALITY ignore  TYPE UE-X2AP-ID                                         PRESENCE mandatory}|
    { ID id-SeNB-UE-X2AP-ID                             CRITICALITY ignore  TYPE UE-X2AP-ID                                         PRESENCE mandatory}|
    { ID id-E-RABs-Admitted-ToBeAdded-ModAckList        CRITICALITY ignore  TYPE E-RABs-Admitted-ToBeAdded-ModAckList       PRESENCE optional}|
    { ID id-E-RABs-Admitted-ToBeModified-ModAckList     CRITICALITY ignore  TYPE E-RABs-Admitted-ToBeModified-ModAckList    PRESENCE optional}|
    { ID id-E-RABs-Admitted-ToBeReleased-ModAckList     CRITICALITY ignore  TYPE E-RABs-Admitted-ToBeReleased-ModAckList    PRESENCE optional}|
    { ID id-E-RABs-NotAdmitted-List                     CRITICALITY ignore  TYPE E-RAB-List                                         PRESENCE optional}|
    { ID id-SeNBtoMeNBContainer                         CRITICALITY ignore  TYPE SeNBtoMeNBContainer                                PRESENCE optional}|
    { ID id-CriticalityDiagnostics                      CRITICALITY ignore  TYPE CriticalityDiagnostics                         PRESENCE optional},
    ...
}

E-RABs-Admitted-ToBeAdded-ModAckList ::= SEQUENCE (SIZE (1..maxnoofBearers)) OF ProtocolIE-Single-Container { {E-RABs-Admitted-ToBeAdded-ModAckItemIEs} }

E-RABs-Admitted-ToBeAdded-ModAckItemIEs X2AP-PROTOCOL-IES ::= {
    { ID id-E-RABs-Admitted-ToBeAdded-ModAckItem    CRITICALITY ignore  TYPE E-RABs-Admitted-ToBeAdded-ModAckItem       PRESENCE mandatory}
}

E-RABs-Admitted-ToBeAdded-ModAckItem ::= CHOICE {
    sCG-Bearer      E-RABs-Admitted-ToBeAdded-ModAckItem-SCG-Bearer,
    split-Bearer    E-RABs-Admitted-ToBeAdded-ModAckItem-Split-Bearer,
    ...
}

E-RABs-Admitted-ToBeAdded-ModAckItem-SCG-Bearer ::= SEQUENCE {
    e-RAB-ID                                E-RAB-ID,
    s1-DL-GTPtunnelEndpoint                 GTPtunnelEndpoint,
    dL-Forwarding-GTPtunnelEndpoint         GTPtunnelEndpoint                                                                   OPTIONAL,
    uL-Forwarding-GTPtunnelEndpoint         GTPtunnelEndpoint                                                                   OPTIONAL,
    iE-Extensions                   ProtocolExtensionContainer { {E-RABs-Admitted-ToBeAdded-ModAckItem-SCG-BearerExtIEs} }  OPTIONAL,
    ...
}

E-RABs-Admitted-ToBeAdded-ModAckItem-SCG-BearerExtIEs X2AP-PROTOCOL-EXTENSION ::= {
    ...
}

E-RABs-Admitted-ToBeAdded-ModAckItem-Split-Bearer ::= SEQUENCE {
    e-RAB-ID                        E-RAB-ID,
    seNB-GTPtunnelEndpoint          GTPtunnelEndpoint,
    iE-Extensions                   ProtocolExtensionContainer { {E-RABs-Admitted-ToBeAdded-ModAckItem-Split-BearerExtIEs} } OPTIONAL,
    ...
}

E-RABs-Admitted-ToBeAdded-ModAckItem-Split-BearerExtIEs X2AP-PROTOCOL-EXTENSION ::= {
    ...
}
E-RABs-Admitted-ToBeModified-ModAckList ::= SEQUENCE (SIZE (1..maxnoofBearers)) OF ProtocolIE-Single-Container { {E-RABs-Admitted-ToBeModified-ModAckItemIEs} }

E-RABs-Admitted-ToBeModified-ModAckItemIEs X2AP-PROTOCOL-IES ::= {
    { ID id-E-RABs-Admitted-ToBeModified-ModAckItem     CRITICALITY ignore  TYPE E-RABs-Admitted-ToBeModified-ModAckItem    PRESENCE mandatory}
}

E-RABs-Admitted-ToBeModified-ModAckItem ::= CHOICE {
    sCG-Bearer      E-RABs-Admitted-ToBeModified-ModAckItem-SCG-Bearer,
    split-Bearer    E-RABs-Admitted-ToBeModified-ModAckItem-Split-Bearer,
    ...
}

E-RABs-Admitted-ToBeModified-ModAckItem-SCG-Bearer ::= SEQUENCE {
    e-RAB-ID                        E-RAB-ID,
    s1-DL-GTPtunnelEndpoint         GTPtunnelEndpoint                                                                   OPTIONAL,
    iE-Extensions                   ProtocolExtensionContainer { {E-RABs-Admitted-ToBeModified-ModAckItem-SCG-BearerExtIEs} } OPTIONAL,
    ...
}

E-RABs-Admitted-ToBeModified-ModAckItem-SCG-BearerExtIEs X2AP-PROTOCOL-EXTENSION ::= {
    ...
}

E-RABs-Admitted-ToBeModified-ModAckItem-Split-Bearer ::= SEQUENCE {
    e-RAB-ID                        E-RAB-ID,
    seNB-GTPtunnelEndpoint          GTPtunnelEndpoint                                                                           OPTIONAL,
    iE-Extensions                   ProtocolExtensionContainer { {E-RABs-Admitted-ToBeModified-ModAckItem-Split-BearerExtIEs} } OPTIONAL,
    ...
}

E-RABs-Admitted-ToBeModified-ModAckItem-Split-BearerExtIEs X2AP-PROTOCOL-EXTENSION ::= {
    ...
}

E-RABs-Admitted-ToBeReleased-ModAckList ::= SEQUENCE (SIZE (1..maxnoofBearers)) OF ProtocolIE-Single-Container { {E-RABs-Admitted-ToBeReleased-ModAckItemIEs} }

E-RABs-Admitted-ToBeReleased-ModAckItemIEs X2AP-PROTOCOL-IES ::= {
    { ID id-E-RABs-Admitted-ToBeReleased-ModAckItem     CRITICALITY ignore  TYPE E-RABs-Admitted-ToReleased-ModAckItem      PRESENCE mandatory}
}

E-RABs-Admitted-ToReleased-ModAckItem ::= CHOICE {
    sCG-Bearer      E-RABs-Admitted-ToBeReleased-ModAckItem-SCG-Bearer,
    split-Bearer    E-RABs-Admitted-ToBeReleased-ModAckItem-Split-Bearer,
    ...
}

E-RABs-Admitted-ToBeReleased-ModAckItem-SCG-Bearer ::= SEQUENCE {
    e-RAB-ID                    E-RAB-ID,
    iE-Extensions               ProtocolExtensionContainer { {E-RABs-Admitted-ToBeReleased-ModAckItem-SCG-BearerExtIEs} }   OPTIONAL,
    ...
}

E-RABs-Admitted-ToBeReleased-ModAckItem-SCG-BearerExtIEs X2AP-PROTOCOL-EXTENSION ::= {
    ...
}

E-RABs-Admitted-ToBeReleased-ModAckItem-Split-Bearer ::= SEQUENCE {
    e-RAB-ID                    E-RAB-ID,
    iE-Extensions               ProtocolExtensionContainer { {E-RABs-Admitted-ToBeReleased-ModAckItem-Split-BearerExtIEs} } OPTIONAL,
    ...
}

E-RABs-Admitted-ToBeReleased-ModAckItem-Split-BearerExtIEs X2AP-PROTOCOL-EXTENSION ::= {
    ...
}

-- **************************************************************
--
-- SENB MODIFICATION REQUEST REJECT
--
-- **************************************************************

SeNBModificationRequestReject ::= SEQUENCE {
    protocolIEs     ProtocolIE-Container    {{SeNBModificationRequestReject-IEs}},
    ...
}

SeNBModificationRequestReject-IEs X2AP-PROTOCOL-IES ::= {
    { ID id-MeNB-UE-X2AP-ID                     CRITICALITY ignore  TYPE UE-X2AP-ID                 PRESENCE mandatory}|
    { ID id-SeNB-UE-X2AP-ID                     CRITICALITY ignore  TYPE UE-X2AP-ID                 PRESENCE mandatory}|
    { ID id-Cause                               CRITICALITY ignore  TYPE Cause                      PRESENCE mandatory}|
    { ID id-CriticalityDiagnostics              CRITICALITY ignore  TYPE CriticalityDiagnostics     PRESENCE optional},
    ...
}

-- **************************************************************
--
-- SENB MODIFICATION REQUIRED
--
-- **************************************************************

SeNBModificationRequired ::= SEQUENCE {
    protocolIEs     ProtocolIE-Container        {{SeNBModificationRequired-IEs}},
    ...
}

SeNBModificationRequired-IEs X2AP-PROTOCOL-IES ::= {
    { ID id-MeNB-UE-X2AP-ID                     CRITICALITY reject  TYPE UE-X2AP-ID                         PRESENCE mandatory}|
    { ID id-SeNB-UE-X2AP-ID                     CRITICALITY reject  TYPE UE-X2AP-ID                         PRESENCE mandatory}|
    { ID id-Cause                               CRITICALITY ignore  TYPE Cause                              PRESENCE mandatory}|
    { ID id-SCGChangeIndication                 CRITICALITY ignore  TYPE SCGChangeIndication                PRESENCE optional}|
    { ID id-E-RABs-ToBeReleased-ModReqd         CRITICALITY ignore  TYPE E-RABs-ToBeReleased-ModReqd        PRESENCE optional}|
    { ID id-SeNBtoMeNBContainer                 CRITICALITY ignore  TYPE SeNBtoMeNBContainer                PRESENCE optional},
    ...
}


E-RABs-ToBeReleased-ModReqd ::= SEQUENCE (SIZE (1..maxnoofBearers)) OF ProtocolIE-Single-Container { {E-RABs-ToBeReleased-ModReqdItemIEs} }

E-RABs-ToBeReleased-ModReqdItemIEs X2AP-PROTOCOL-IES ::= {
    { ID id-E-RABs-ToBeReleased-ModReqdItem  CRITICALITY ignore     TYPE E-RABs-ToBeReleased-ModReqdItem    PRESENCE mandatory },
    ...
}

E-RABs-ToBeReleased-ModReqdItem ::= SEQUENCE {
    e-RAB-ID                        E-RAB-ID,
    cause                           Cause,
    iE-Extensions                   ProtocolExtensionContainer { {E-RABs-ToBeReleased-ModReqdItemExtIEs} } OPTIONAL,
    ...
}

E-RABs-ToBeReleased-ModReqdItemExtIEs X2AP-PROTOCOL-EXTENSION ::= {
    ...
}

-- **************************************************************
--
-- SENB MODIFICATION CONFIRM
--
-- **************************************************************

SeNBModificationConfirm ::= SEQUENCE {
    protocolIEs     ProtocolIE-Container    {{SeNBModificationConfirm-IEs}},
    ...
}

SeNBModificationConfirm-IEs X2AP-PROTOCOL-IES ::= {
    { ID id-MeNB-UE-X2AP-ID                     CRITICALITY ignore  TYPE UE-X2AP-ID                 PRESENCE mandatory}|
    { ID id-SeNB-UE-X2AP-ID                     CRITICALITY ignore  TYPE UE-X2AP-ID                 PRESENCE mandatory}|
    { ID id-MeNBtoSeNBContainer                 CRITICALITY ignore  TYPE MeNBtoSeNBContainer        PRESENCE optional}|
    { ID id-CriticalityDiagnostics              CRITICALITY ignore  TYPE CriticalityDiagnostics     PRESENCE optional},
    ...
}

-- **************************************************************
--
-- SENB MODIFICATION REFUSE
--
-- **************************************************************

SeNBModificationRefuse ::= SEQUENCE {
    protocolIEs     ProtocolIE-Container        {{SeNBModificationRefuse-IEs}},
    ...
}

SeNBModificationRefuse-IEs X2AP-PROTOCOL-IES ::= {
    { ID id-MeNB-UE-X2AP-ID                     CRITICALITY ignore  TYPE UE-X2AP-ID                 PRESENCE mandatory}|
    { ID id-SeNB-UE-X2AP-ID                     CRITICALITY ignore  TYPE UE-X2AP-ID                 PRESENCE mandatory}|
    { ID id-Cause                               CRITICALITY ignore  TYPE Cause                      PRESENCE mandatory}|
    { ID id-MeNBtoSeNBContainer                 CRITICALITY ignore  TYPE MeNBtoSeNBContainer        PRESENCE optional}|
    { ID id-CriticalityDiagnostics              CRITICALITY ignore  TYPE CriticalityDiagnostics     PRESENCE optional},
    ...
}

-- **************************************************************
--
-- SENB RELEASE REQUEST
--
-- **************************************************************

SeNBReleaseRequest ::= SEQUENCE {
    protocolIEs     ProtocolIE-Container        {{SeNBReleaseRequest-IEs}},
    ...
}

SeNBReleaseRequest-IEs X2AP-PROTOCOL-IES ::= {
    { ID id-MeNB-UE-X2AP-ID                         CRITICALITY reject  TYPE UE-X2AP-ID                                 PRESENCE mandatory}|
    { ID id-SeNB-UE-X2AP-ID                         CRITICALITY reject  TYPE UE-X2AP-ID                                 PRESENCE optional}|
    { ID id-Cause                                   CRITICALITY ignore  TYPE Cause                                      PRESENCE optional}|
    { ID id-E-RABs-ToBeReleased-List-RelReq         CRITICALITY ignore  TYPE E-RABs-ToBeReleased-List-RelReq        PRESENCE optional},
    ...
}
E-RABs-ToBeReleased-List-RelReq ::= SEQUENCE (SIZE(1..maxnoofBearers)) OF ProtocolIE-Single-Container { {E-RABs-ToBeReleased-RelReqItemIEs} }

E-RABs-ToBeReleased-RelReqItemIEs X2AP-PROTOCOL-IES ::= {
    { ID id-E-RABs-ToBeReleased-RelReqItem      CRITICALITY ignore  TYPE E-RABs-ToBeReleased-RelReqItem     PRESENCE mandatory},
    ...
}

E-RABs-ToBeReleased-RelReqItem ::= CHOICE {
    sCG-Bearer      E-RABs-ToBeReleased-RelReqItem-SCG-Bearer,
    split-Bearer    E-RABs-ToBeReleased-RelReqItem-Split-Bearer,
    ...
}

E-RABs-ToBeReleased-RelReqItem-SCG-Bearer ::= SEQUENCE {
    e-RAB-ID                        E-RAB-ID,
    uL-GTPtunnelEndpoint            GTPtunnelEndpoint                                                               OPTIONAL,
    dL-GTPtunnelEndpoint            GTPtunnelEndpoint                                                               OPTIONAL,
    iE-Extensions                   ProtocolExtensionContainer { {E-RABs-ToBeReleased-RelReqItem-SCG-BearerExtIEs} } OPTIONAL,
    ...
}

E-RABs-ToBeReleased-RelReqItem-SCG-BearerExtIEs X2AP-PROTOCOL-EXTENSION ::= {
    ...
}

E-RABs-ToBeReleased-RelReqItem-Split-Bearer ::= SEQUENCE {
    e-RAB-ID                        E-RAB-ID,
    dL-GTPtunnelEndpoint            GTPtunnelEndpoint                                                               OPTIONAL,
    iE-Extensions                   ProtocolExtensionContainer { {E-RABs-ToBeReleased-RelReqItem-Split-BearerExtIEs} } OPTIONAL,
    ...
}

E-RABs-ToBeReleased-RelReqItem-Split-BearerExtIEs X2AP-PROTOCOL-EXTENSION ::= {
    ...
}

-- **************************************************************
--
-- SENB RELEASE REQUIRED
--
-- **************************************************************

SeNBReleaseRequired ::= SEQUENCE {
    protocolIEs     ProtocolIE-Container    {{SeNBReleaseRequired-IEs}},
    ...
}

SeNBReleaseRequired-IEs X2AP-PROTOCOL-IES ::= {
    { ID id-MeNB-UE-X2AP-ID                     CRITICALITY reject  TYPE UE-X2AP-ID     PRESENCE mandatory}|
    { ID id-SeNB-UE-X2AP-ID                     CRITICALITY reject  TYPE UE-X2AP-ID     PRESENCE mandatory}|
    { ID id-Cause                               CRITICALITY ignore  TYPE Cause          PRESENCE mandatory},
    ...
}

-- **************************************************************
--
-- SENB RELEASE CONFIRM
--
-- **************************************************************

SeNBReleaseConfirm ::= SEQUENCE {
    protocolIEs     ProtocolIE-Container    {{SeNBReleaseConfirm-IEs}},
    ...
}

SeNBReleaseConfirm-IEs X2AP-PROTOCOL-IES ::= {
    { ID id-MeNB-UE-X2AP-ID                         CRITICALITY ignore  TYPE UE-X2AP-ID                                 PRESENCE mandatory}|
    { ID id-SeNB-UE-X2AP-ID                         CRITICALITY ignore  TYPE UE-X2AP-ID                                 PRESENCE mandatory}|
    { ID id-E-RABs-ToBeReleased-List-RelConf        CRITICALITY ignore  TYPE E-RABs-ToBeReleased-List-RelConf       PRESENCE optional}|
    { ID id-CriticalityDiagnostics                  CRITICALITY ignore  TYPE CriticalityDiagnostics                 PRESENCE optional},
    ...
}
E-RABs-ToBeReleased-List-RelConf ::= SEQUENCE (SIZE(1..maxnoofBearers)) OF ProtocolIE-Single-Container { {E-RABs-ToBeReleased-RelConfItemIEs} }

E-RABs-ToBeReleased-RelConfItemIEs X2AP-PROTOCOL-IES ::= {
    { ID id-E-RABs-ToBeReleased-RelConfItem     CRITICALITY ignore      TYPE E-RABs-ToBeReleased-RelConfItem        PRESENCE mandatory},
    ...
}

E-RABs-ToBeReleased-RelConfItem ::= CHOICE {
    sCG-Bearer      E-RABs-ToBeReleased-RelConfItem-SCG-Bearer,
    split-Bearer    E-RABs-ToBeReleased-RelConfItem-Split-Bearer,
    ...
}

E-RABs-ToBeReleased-RelConfItem-SCG-Bearer ::= SEQUENCE {
    e-RAB-ID                        E-RAB-ID,
    uL-GTPtunnelEndpoint            GTPtunnelEndpoint                                                               OPTIONAL,
    dL-GTPtunnelEndpoint            GTPtunnelEndpoint                                                               OPTIONAL,
    iE-Extensions                   ProtocolExtensionContainer { {E-RABs-ToBeReleased-RelConfItem-SCG-BearerExtIEs} } OPTIONAL,
    ...
}

E-RABs-ToBeReleased-RelConfItem-SCG-BearerExtIEs X2AP-PROTOCOL-EXTENSION ::= {
    ...
}

E-RABs-ToBeReleased-RelConfItem-Split-Bearer ::= SEQUENCE {
    e-RAB-ID                        E-RAB-ID,
    dL-GTPtunnelEndpoint            GTPtunnelEndpoint                                                   OPTIONAL,
    iE-Extensions                   ProtocolExtensionContainer { {E-RABs-ToBeReleased-RelConfItem-Split-BearerExtIEs} } OPTIONAL,
    ...
}

E-RABs-ToBeReleased-RelConfItem-Split-BearerExtIEs X2AP-PROTOCOL-EXTENSION ::= {
    ...
}

-- **************************************************************
--
-- SENB COUNTER CHECK REQUEST
--
-- **************************************************************

SeNBCounterCheckRequest ::= SEQUENCE {
    protocolIEs     ProtocolIE-Container    {{SeNBCounterCheckRequest-IEs}},
    ...
}

SeNBCounterCheckRequest-IEs X2AP-PROTOCOL-IES ::= {
    { ID id-MeNB-UE-X2AP-ID                             CRITICALITY ignore  TYPE UE-X2AP-ID                                 PRESENCE mandatory}|
    { ID id-SeNB-UE-X2AP-ID                             CRITICALITY ignore  TYPE UE-X2AP-ID                                 PRESENCE mandatory}|
    { ID id-E-RABs-SubjectToCounterCheck-List           CRITICALITY ignore  TYPE E-RABs-SubjectToCounterCheck-List  PRESENCE mandatory},
    ...
}
E-RABs-SubjectToCounterCheck-List ::= SEQUENCE (SIZE(1..maxnoofBearers)) OF ProtocolIE-Single-Container { {E-RABs-SubjectToCounterCheckItemIEs} }

E-RABs-SubjectToCounterCheckItemIEs X2AP-PROTOCOL-IES ::= {
    { ID id-E-RABs-SubjectToCounterCheckItem    CRITICALITY ignore  TYPE E-RABs-SubjectToCounterCheckItem       PRESENCE mandatory},
    ...
}

E-RABs-SubjectToCounterCheckItem ::= SEQUENCE {
    e-RAB-ID                        E-RAB-ID,
    uL-Count                        INTEGER (0..4294967295),
    dL-Count                        INTEGER (0..4294967295),
    iE-Extensions                   ProtocolExtensionContainer { {E-RABs-SubjectToCounterCheckItemExtIEs} } OPTIONAL,
    ...
}

E-RABs-SubjectToCounterCheckItemExtIEs X2AP-PROTOCOL-EXTENSION ::= {
    ...
}

-- **************************************************************
--
-- X2 REMOVAL REQUEST
--
-- **************************************************************

X2RemovalRequest ::= SEQUENCE {
    protocolIEs     ProtocolIE-Container    {{X2RemovalRequest-IEs}},
    ...
}

X2RemovalRequest-IEs X2AP-PROTOCOL-IES ::= {
    { ID id-GlobalENB-ID                CRITICALITY reject  TYPE GlobalENB-ID           PRESENCE mandatory},
...
}



-- **************************************************************
--
-- X2 REMOVAL RESPONSE
--
-- **************************************************************

X2RemovalResponse ::= SEQUENCE {
    protocolIEs     ProtocolIE-Container    {{X2RemovalResponse-IEs}},
    ...
}

X2RemovalResponse-IEs X2AP-PROTOCOL-IES ::= {
    { ID id-GlobalENB-ID                CRITICALITY reject  TYPE GlobalENB-ID               PRESENCE mandatory}|
    { ID id-CriticalityDiagnostics      CRITICALITY ignore  TYPE CriticalityDiagnostics     PRESENCE optional},
    ...
}



-- **************************************************************
--
-- X2 REMOVAL FAILURE
--
-- **************************************************************

X2RemovalFailure ::= SEQUENCE {
    protocolIEs     ProtocolIE-Container    {{X2RemovalFailure-IEs}},
    ...
}

X2RemovalFailure-IEs X2AP-PROTOCOL-IES ::= {
    { ID id-Cause                       CRITICALITY ignore  TYPE Cause                          PRESENCE mandatory}|
    { ID id-CriticalityDiagnostics      CRITICALITY ignore  TYPE CriticalityDiagnostics         PRESENCE optional},
    ...
}

END
