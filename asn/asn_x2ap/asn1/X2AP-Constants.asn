-- **************************************************************
--
-- Constant definitions
--
-- **************************************************************

X2AP-Constants {
itu-t (0) identified-organization (4) etsi (0) mobileDomain (0) 
eps-Access (21) modules (3) x2ap (2) version1 (1) x2ap-Constants (4) }

DEFINITIONS AUTOMATIC TAGS ::= 

BEGIN

IMPORTS
    ProcedureCode,
    ProtocolIE-ID
FROM X2AP-CommonDataTypes;

-- **************************************************************
--
-- Elementary Procedures
--
-- **************************************************************

id-handoverPreparation                                          ProcedureCode ::= 0
id-handoverCancel                                               ProcedureCode ::= 1
id-loadIndication                                               ProcedureCode ::= 2
id-errorIndication                                              ProcedureCode ::= 3
id-snStatusTransfer                                             ProcedureCode ::= 4
id-uEContextRelease                                             ProcedureCode ::= 5
id-x2Setup                                                      ProcedureCode ::= 6
id-reset                                                        ProcedureCode ::= 7
id-eNBConfigurationUpdate                                       ProcedureCode ::= 8
id-resourceStatusReportingInitiation                            ProcedureCode ::= 9
id-resourceStatusReporting                                      ProcedureCode ::= 10
id-privateMessage                                               ProcedureCode ::= 11
id-mobilitySettingsChange                                       ProcedureCode ::= 12
id-rLFIndication                                                ProcedureCode ::= 13
id-handoverReport                                               ProcedureCode ::= 14
id-cellActivation                                               ProcedureCode ::= 15
id-x2Release                                                    ProcedureCode ::= 16
id-x2MessageTransfer                                            ProcedureCode ::= 17
id-x2Removal                                                    ProcedureCode ::= 18
id-seNBAdditionPreparation                                      ProcedureCode ::= 19
id-seNBReconfigurationCompletion                                ProcedureCode ::= 20
id-meNBinitiatedSeNBModificationPreparation                     ProcedureCode ::= 21
id-seNBinitiatedSeNBModification                                ProcedureCode ::= 22
id-meNBinitiatedSeNBRelease                                     ProcedureCode ::= 23
id-seNBinitiatedSeNBRelease                                     ProcedureCode ::= 24
id-seNBCounterCheck                                             ProcedureCode ::= 25


-- **************************************************************
--
-- Lists
--
-- **************************************************************

maxEARFCN                                   INTEGER ::= 65535
maxEARFCNPlusOne                            INTEGER ::= 65536
newmaxEARFCN                                INTEGER ::= 262143
maxInterfaces                               INTEGER ::= 16
maxCellineNB                                INTEGER ::= 256
maxnoofBands                                INTEGER ::= 16
maxnoofBearers                              INTEGER ::= 256
maxNrOfErrors                               INTEGER ::= 256
maxnoofPDCP-SN                              INTEGER ::= 16
maxnoofEPLMNs                               INTEGER ::= 15
maxnoofEPLMNsPlusOne                        INTEGER ::= 16
maxnoofForbLACs                             INTEGER ::= 4096
maxnoofForbTACs                             INTEGER ::= 4096
maxnoofBPLMNs                               INTEGER ::= 6
maxnoofNeighbours                           INTEGER ::= 512
maxnoofPRBs                                 INTEGER ::= 110
maxPools                                    INTEGER ::= 16
maxnoofCells                                INTEGER ::= 16
maxnoofMBSFN                                INTEGER ::= 8
maxFailedMeasObjects                        INTEGER ::= 32
maxnoofCellIDforMDT                         INTEGER ::= 32
maxnoofTAforMDT                             INTEGER ::= 8
maxnoofMBMSServiceAreaIdentities            INTEGER ::= 256
maxnoofMDTPLMNs                             INTEGER ::= 16
maxnoofCoMPHypothesisSet                    INTEGER ::= 256
maxnoofCoMPCells                            INTEGER ::= 32
maxUEReport                                 INTEGER ::= 128
maxCellReport                               INTEGER ::= 9
maxnoofPA                                   INTEGER ::= 3


-- **************************************************************
--
-- IEs
--
-- **************************************************************

id-E-RABs-Admitted-Item                                                     ProtocolIE-ID ::= 0
id-E-RABs-Admitted-List                                                     ProtocolIE-ID ::= 1
id-E-RAB-Item                                                               ProtocolIE-ID ::= 2
id-E-RABs-NotAdmitted-List                                                  ProtocolIE-ID ::= 3
id-E-RABs-ToBeSetup-Item                                                    ProtocolIE-ID ::= 4
id-Cause                                                                    ProtocolIE-ID ::= 5
id-CellInformation                                                          ProtocolIE-ID ::= 6
id-CellInformation-Item                                                     ProtocolIE-ID ::= 7
id-New-eNB-UE-X2AP-ID                                                       ProtocolIE-ID ::= 9
id-Old-eNB-UE-X2AP-ID                                                       ProtocolIE-ID ::= 10
id-TargetCell-ID                                                            ProtocolIE-ID ::= 11
id-TargeteNBtoSource-eNBTransparentContainer                                ProtocolIE-ID ::= 12
id-TraceActivation                                                          ProtocolIE-ID ::= 13
id-UE-ContextInformation                                                    ProtocolIE-ID ::= 14
id-UE-HistoryInformation                                                    ProtocolIE-ID ::= 15
id-UE-X2AP-ID                                                               ProtocolIE-ID ::= 16
id-CriticalityDiagnostics                                                   ProtocolIE-ID ::= 17
id-E-RABs-SubjectToStatusTransfer-List                                      ProtocolIE-ID ::= 18
id-E-RABs-SubjectToStatusTransfer-Item                                      ProtocolIE-ID ::= 19
id-ServedCells                                                              ProtocolIE-ID ::= 20
id-GlobalENB-ID                                                             ProtocolIE-ID ::= 21
id-TimeToWait                                                               ProtocolIE-ID ::= 22
id-GUMMEI-ID                                                                ProtocolIE-ID ::= 23
id-GUGroupIDList                                                            ProtocolIE-ID ::= 24
id-ServedCellsToAdd                                                         ProtocolIE-ID ::= 25
id-ServedCellsToModify                                                      ProtocolIE-ID ::= 26
id-ServedCellsToDelete                                                      ProtocolIE-ID ::= 27
id-Registration-Request                                                     ProtocolIE-ID ::= 28
id-CellToReport                                                             ProtocolIE-ID ::= 29
id-ReportingPeriodicity                                                     ProtocolIE-ID ::= 30
id-CellToReport-Item                                                        ProtocolIE-ID ::= 31
id-CellMeasurementResult                                                    ProtocolIE-ID ::= 32
id-CellMeasurementResult-Item                                               ProtocolIE-ID ::= 33
id-GUGroupIDToAddList                                                       ProtocolIE-ID ::= 34
id-GUGroupIDToDeleteList                                                    ProtocolIE-ID ::= 35
id-SRVCCOperationPossible                                                   ProtocolIE-ID ::= 36
id-Measurement-ID                                                           ProtocolIE-ID ::= 37
id-ReportCharacteristics                                                    ProtocolIE-ID ::= 38
id-ENB1-Measurement-ID                                                      ProtocolIE-ID ::= 39
id-ENB2-Measurement-ID                                                      ProtocolIE-ID ::= 40
id-Number-of-Antennaports                                                   ProtocolIE-ID ::= 41
id-CompositeAvailableCapacityGroup                                          ProtocolIE-ID ::= 42
id-ENB1-Cell-ID                                                             ProtocolIE-ID ::= 43
id-ENB2-Cell-ID                                                             ProtocolIE-ID ::= 44
id-ENB2-Proposed-Mobility-Parameters                                        ProtocolIE-ID ::= 45
id-ENB1-Mobility-Parameters                                                 ProtocolIE-ID ::= 46
id-ENB2-Mobility-Parameters-Modification-Range                              ProtocolIE-ID ::= 47
id-FailureCellPCI                                                           ProtocolIE-ID ::= 48
id-Re-establishmentCellECGI                                                 ProtocolIE-ID ::= 49
id-FailureCellCRNTI                                                         ProtocolIE-ID ::= 50
id-ShortMAC-I                                                               ProtocolIE-ID ::= 51
id-SourceCellECGI                                                           ProtocolIE-ID ::= 52
id-FailureCellECGI                                                          ProtocolIE-ID ::= 53
id-HandoverReportType                                                       ProtocolIE-ID ::= 54
id-PRACH-Configuration                                                      ProtocolIE-ID ::= 55
id-MBSFN-Subframe-Info                                                      ProtocolIE-ID ::= 56
id-ServedCellsToActivate                                                    ProtocolIE-ID ::= 57
id-ActivatedCellList                                                        ProtocolIE-ID ::= 58
id-DeactivationIndication                                                   ProtocolIE-ID ::= 59
id-UE-RLF-Report-Container                                                  ProtocolIE-ID ::= 60
id-ABSInformation                                                           ProtocolIE-ID ::= 61
id-InvokeIndication                                                         ProtocolIE-ID ::= 62
id-ABS-Status                                                               ProtocolIE-ID ::= 63
id-PartialSuccessIndicator                                                  ProtocolIE-ID ::= 64
id-MeasurementInitiationResult-List                                         ProtocolIE-ID ::= 65
id-MeasurementInitiationResult-Item                                         ProtocolIE-ID ::= 66
id-MeasurementFailureCause-Item                                             ProtocolIE-ID ::= 67
id-CompleteFailureCauseInformation-List                                     ProtocolIE-ID ::= 68
id-CompleteFailureCauseInformation-Item                                     ProtocolIE-ID ::= 69
id-CSG-Id                                                                   ProtocolIE-ID ::= 70
id-CSGMembershipStatus                                                      ProtocolIE-ID ::= 71
id-MDTConfiguration                                                         ProtocolIE-ID ::= 72
id-ManagementBasedMDTallowed                                                ProtocolIE-ID ::= 74
id-RRCConnSetupIndicator                                                    ProtocolIE-ID ::= 75
id-NeighbourTAC                                                             ProtocolIE-ID ::= 76
id-Time-UE-StayedInCell-EnhancedGranularity                                 ProtocolIE-ID ::= 77
id-RRCConnReestabIndicator                                                  ProtocolIE-ID ::= 78
id-MBMS-Service-Area-List                                                   ProtocolIE-ID ::= 79
id-HO-cause                                                                 ProtocolIE-ID ::= 80
id-TargetCellInUTRAN                                                        ProtocolIE-ID ::= 81
id-MobilityInformation                                                      ProtocolIE-ID ::= 82
id-SourceCellCRNTI                                                          ProtocolIE-ID ::= 83
id-MultibandInfoList                                                        ProtocolIE-ID ::= 84
id-M3Configuration                                                          ProtocolIE-ID ::= 85
id-M4Configuration                                                          ProtocolIE-ID ::= 86
id-M5Configuration                                                          ProtocolIE-ID ::= 87
id-MDT-Location-Info                                                        ProtocolIE-ID ::= 88
id-ManagementBasedMDTPLMNList                                               ProtocolIE-ID ::= 89
id-SignallingBasedMDTPLMNList                                               ProtocolIE-ID ::= 90
id-ReceiveStatusOfULPDCPSDUsExtended                                        ProtocolIE-ID ::= 91
id-ULCOUNTValueExtended                                                     ProtocolIE-ID ::= 92
id-DLCOUNTValueExtended                                                     ProtocolIE-ID ::= 93
id-eARFCNExtension                                                          ProtocolIE-ID ::= 94
id-UL-EARFCNExtension                                                       ProtocolIE-ID ::= 95
id-DL-EARFCNExtension                                                       ProtocolIE-ID ::= 96
id-AdditionalSpecialSubframe-Info                                           ProtocolIE-ID ::= 97
id-Masked-IMEISV                                                            ProtocolIE-ID ::= 98
id-IntendedULDLConfiguration                                                ProtocolIE-ID ::= 99
id-ExtendedULInterferenceOverloadInfo                                       ProtocolIE-ID ::= 100
id-RNL-Header                                                               ProtocolIE-ID ::= 101
id-x2APMessage                                                              ProtocolIE-ID ::= 102
id-ExpectedUEBehaviour                                                      ProtocolIE-ID ::= 104
id-UE-HistoryInformationFromTheUE                                           ProtocolIE-ID ::= 105
id-DynamicDLTransmissionInformation                                         ProtocolIE-ID ::= 106
id-UE-RLF-Report-Container-for-extended-bands                               ProtocolIE-ID ::= 107
id-CoMPInformation                                                          ProtocolIE-ID ::= 108
id-ReportingPeriodicityRSRPMR                                               ProtocolIE-ID ::= 109
id-RSRPMRList                                                               ProtocolIE-ID ::= 110
id-MeNB-UE-X2AP-ID                                                          ProtocolIE-ID ::= 111
id-SeNB-UE-X2AP-ID                                                          ProtocolIE-ID ::= 112
id-UE-SecurityCapabilities                                                  ProtocolIE-ID ::= 113
id-SeNBSecurityKey                                                          ProtocolIE-ID ::= 114
id-UEAggregateMaximumBitRate                                                ProtocolIE-ID ::= 115
id-ServingPLMN                                                              ProtocolIE-ID ::= 116
id-E-RABs-ToBeAdded-List                                                    ProtocolIE-ID ::= 117
id-E-RABs-ToBeAdded-Item                                                    ProtocolIE-ID ::= 118
id-MeNBtoSeNBContainer                                                      ProtocolIE-ID ::= 119
id-E-RABs-Admitted-ToBeAdded-List                                           ProtocolIE-ID ::= 120
id-E-RABs-Admitted-ToBeAdded-Item                                           ProtocolIE-ID ::= 121
id-SeNBtoMeNBContainer                                                      ProtocolIE-ID ::= 122
id-ResponseInformationSeNBReconfComp                                        ProtocolIE-ID ::= 123
id-UE-ContextInformationSeNBModReq                                          ProtocolIE-ID ::= 124
id-E-RABs-ToBeAdded-ModReqItem                                              ProtocolIE-ID ::= 125
id-E-RABs-ToBeModified-ModReqItem                                           ProtocolIE-ID ::= 126
id-E-RABs-ToBeReleased-ModReqItem                                           ProtocolIE-ID ::= 127
id-E-RABs-Admitted-ToBeAdded-ModAckList                                     ProtocolIE-ID ::= 128
id-E-RABs-Admitted-ToBeModified-ModAckList                                  ProtocolIE-ID ::= 129
id-E-RABs-Admitted-ToBeReleased-ModAckList                                  ProtocolIE-ID ::= 130
id-E-RABs-Admitted-ToBeAdded-ModAckItem                                     ProtocolIE-ID ::= 131
id-E-RABs-Admitted-ToBeModified-ModAckItem                                  ProtocolIE-ID ::= 132
id-E-RABs-Admitted-ToBeReleased-ModAckItem                                  ProtocolIE-ID ::= 133
id-E-RABs-ToBeReleased-ModReqd                                              ProtocolIE-ID ::= 134
id-E-RABs-ToBeReleased-ModReqdItem                                          ProtocolIE-ID ::= 135
id-SCGChangeIndication                                                      ProtocolIE-ID ::= 136
id-E-RABs-ToBeReleased-List-RelReq                                          ProtocolIE-ID ::= 137
id-E-RABs-ToBeReleased-RelReqItem                                           ProtocolIE-ID ::= 138
id-E-RABs-ToBeReleased-List-RelConf                                         ProtocolIE-ID ::= 139
id-E-RABs-ToBeReleased-RelConfItem                                          ProtocolIE-ID ::= 140
id-E-RABs-SubjectToCounterCheck-List                                        ProtocolIE-ID ::= 141
id-E-RABs-SubjectToCounterCheckItem                                         ProtocolIE-ID ::= 142

END
