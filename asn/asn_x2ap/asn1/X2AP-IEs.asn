-- **************************************************************
--
-- Information Element Definitions
--
-- **************************************************************

X2AP-IEs {
itu-t (0) identified-organization (4) etsi (0) mobileDomain (0) 
eps-Access (21) modules (3) x2ap (2) version1 (1) x2ap-IEs (2) }

DEFINITIONS AUTOMATIC TAGS ::= 

BEGIN

IMPORTS
    
    id-E-RAB-Item,
    id-Number-of-Antennaports,
    id-MBSFN-Subframe-Info,
    id-PRACH-Configuration,
    id-CSG-Id,
    id-MDTConfiguration,
    id-SignallingBasedMDTPLMNList,
    id-MultibandInfoList,
    id-NeighbourTAC,
    id-Time-UE-StayedInCell-EnhancedGranularity,
    id-MBMS-Service-Area-List,
    id-HO-cause,
    id-eARFCNExtension,
    id-DL-EARFCNExtension,
    id-UL-EARFCNExtension,
    id-M3Configuration,
    id-M4Configuration,
    id-M5Configuration,
    id-MDT-Location-Info,
    id-AdditionalSpecialSubframe-Info,
    maxnoofBearers,
    maxCellineNB,
    maxEARFCN,
    maxEARFCNPlusOne,
    newmaxEARFCN,
    maxInterfaces,
    
    maxnoofBands,
    maxnoofBPLMNs,
    maxnoofCells,
    maxnoofEPLMNs,
    maxnoofEPLMNsPlusOne,
    maxnoofForbLACs,
    maxnoofForbTACs,
    maxnoofNeighbours,
    maxnoofPRBs,
    maxNrOfErrors,
    maxPools,
    maxnoofMBSFN,
    maxnoofTAforMDT,
    maxnoofCellIDforMDT,
    maxnoofMBMSServiceAreaIdentities,
    maxnoofMDTPLMNs,
    maxnoofCoMPHypothesisSet,
    maxnoofCoMPCells,
    maxUEReport,
    maxCellReport,
    maxnoofPA

FROM X2AP-Constants

    Criticality,
    ProcedureCode,
    ProtocolIE-ID,
    TriggeringMessage
FROM X2AP-CommonDataTypes

    ProtocolExtensionContainer{},
    ProtocolIE-Single-Container{},
    
    X2AP-PROTOCOL-EXTENSION,
    X2AP-PROTOCOL-IES
FROM X2AP-Containers;

-- A

ABSInformation ::= CHOICE {
    fdd                 ABSInformationFDD,
    tdd                 ABSInformationTDD,
    abs-inactive        NULL,
    ...
}

ABSInformationFDD ::= SEQUENCE {
    abs-pattern-info                    BIT STRING (SIZE(40)),
    numberOfCellSpecificAntennaPorts    ENUMERATED {one, two, four, ...},
    measurement-subset                  BIT STRING (SIZE(40)),
    iE-Extensions                       ProtocolExtensionContainer { { ABSInformationFDD-ExtIEs} } OPTIONAL,
    ...
}

ABSInformationFDD-ExtIEs X2AP-PROTOCOL-EXTENSION ::= {
    ...
}

ABSInformationTDD ::= SEQUENCE {
    abs-pattern-info                    BIT STRING (SIZE(1..70, ...)),
    numberOfCellSpecificAntennaPorts    ENUMERATED {one, two, four, ...},
    measurement-subset                  BIT STRING (SIZE(1..70, ...)),
    iE-Extensions                       ProtocolExtensionContainer { { ABSInformationTDD-ExtIEs} } OPTIONAL,
    ...
}

ABSInformationTDD-ExtIEs X2AP-PROTOCOL-EXTENSION ::= {
    ...
}

ABS-Status ::= SEQUENCE {
    dL-ABS-status                               DL-ABS-status,
    usableABSInformation                        UsableABSInformation,
    iE-Extensions                               ProtocolExtensionContainer { {ABS-Status-ExtIEs} } OPTIONAL,
    ...
}

ABS-Status-ExtIEs X2AP-PROTOCOL-EXTENSION ::= {
    ...
}

DL-ABS-status::= INTEGER (0..100)

AdditionalSpecialSubframe-Info ::=      SEQUENCE {
    additionalspecialSubframePatterns       AdditionalSpecialSubframePatterns,
    cyclicPrefixDL                          CyclicPrefixDL,
    cyclicPrefixUL                          CyclicPrefixUL,
    iE-Extensions                           ProtocolExtensionContainer { { AdditionalSpecialSubframe-Info-ExtIEs} } OPTIONAL,
    ...
}

AdditionalSpecialSubframe-Info-ExtIEs X2AP-PROTOCOL-EXTENSION ::= {
    ...
}

AdditionalSpecialSubframePatterns ::= ENUMERATED {
    ssp0,
    ssp1,
    ssp2,
    ssp3,
    ssp4,
    ssp5,
    ssp6,
    ssp7,
    ssp8,
    ssp9,
    ...
}

AS-SecurityInformation ::= SEQUENCE {
    key-eNodeB-star     Key-eNodeB-Star,
    nextHopChainingCount            NextHopChainingCount,
    iE-Extensions                       ProtocolExtensionContainer { { AS-SecurityInformation-ExtIEs} } OPTIONAL,
    ...
}

AS-SecurityInformation-ExtIEs X2AP-PROTOCOL-EXTENSION ::= {
    ...
}


AllocationAndRetentionPriority ::= SEQUENCE {
    priorityLevel               PriorityLevel,
    pre-emptionCapability       Pre-emptionCapability,
    pre-emptionVulnerability    Pre-emptionVulnerability,
    iE-Extensions               ProtocolExtensionContainer { {AllocationAndRetentionPriority-ExtIEs} } OPTIONAL,
    ...
}

AllocationAndRetentionPriority-ExtIEs X2AP-PROTOCOL-EXTENSION ::= {
    ...
}

AreaScopeOfMDT ::= CHOICE { 
    cellBased                   CellBasedMDT,
    tABased                     TABasedMDT,
    pLMNWide                    NULL,
    ...,
    tAIBased                    TAIBasedMDT
}

-- B

BenefitMetric ::= INTEGER (-101..100, ...)

BitRate ::= INTEGER (0..10000000000)
BroadcastPLMNs-Item ::= SEQUENCE (SIZE(1..maxnoofBPLMNs)) OF PLMN-Identity


-- C

CapacityValue ::= INTEGER (0..100)

CellCapacityClassValue ::= INTEGER (1..100, ...)

Cause ::= CHOICE {
    radioNetwork        CauseRadioNetwork,
    transport           CauseTransport,
    protocol            CauseProtocol,
    misc                CauseMisc,
    ...
}

CauseMisc ::= ENUMERATED {
    control-processing-overload,
    hardware-failure,
    om-intervention,
    not-enough-user-plane-processing-resources,
    unspecified,
    ...
}

CauseProtocol ::= ENUMERATED {
    transfer-syntax-error,
    abstract-syntax-error-reject,
    abstract-syntax-error-ignore-and-notify,
    message-not-compatible-with-receiver-state,
    semantic-error,
    unspecified,
    abstract-syntax-error-falsely-constructed-message,
    ...
}

CauseRadioNetwork ::= ENUMERATED {
    handover-desirable-for-radio-reasons,
    time-critical-handover,
    resource-optimisation-handover,
    reduce-load-in-serving-cell,
    partial-handover,
    unknown-new-eNB-UE-X2AP-ID, 
    unknown-old-eNB-UE-X2AP-ID, 
    unknown-pair-of-UE-X2AP-ID,
    ho-target-not-allowed,
    tx2relocoverall-expiry,
    trelocprep-expiry,
    cell-not-available,
    no-radio-resources-available-in-target-cell,
    invalid-MME-GroupID,
    unknown-MME-Code,
    encryption-and-or-integrity-protection-algorithms-not-supported,
    reportCharacteristicsEmpty,
    noReportPeriodicity,
    existingMeasurementID,
    unknown-eNB-Measurement-ID,
    measurement-temporarily-not-available,
    unspecified,
    ...,
    load-balancing,
    handover-optimisation,
    value-out-of-allowed-range,
    multiple-E-RAB-ID-instances,
    switch-off-ongoing,
    not-supported-QCI-value,
    measurement-not-supported-for-the-object,
    tDCoverall-expiry,
    tDCprep-expiry

}

CauseTransport ::= ENUMERATED {
    transport-resource-unavailable,
    unspecified,
    ...
}

CellBasedMDT::= SEQUENCE {
    cellIdListforMDT    CellIdListforMDT,
    iE-Extensions       ProtocolExtensionContainer { {CellBasedMDT-ExtIEs} } OPTIONAL,
    ...
}

CellBasedMDT-ExtIEs X2AP-PROTOCOL-EXTENSION ::= {
    ...
}

CellIdListforMDT ::= SEQUENCE (SIZE(1..maxnoofCellIDforMDT)) OF ECGI

Cell-Size ::= ENUMERATED {verysmall, small, medium, large, ... }


CellType ::= SEQUENCE {
    cell-Size                       Cell-Size,
    iE-Extensions                   ProtocolExtensionContainer { { CellType-ExtIEs}}    OPTIONAL,
    ...
}

CellType-ExtIEs X2AP-PROTOCOL-EXTENSION ::= {
    ...
}

CoMPHypothesisSet ::= SEQUENCE (SIZE(1..maxnoofCoMPCells)) OF CoMPHypothesisSetItem

CoMPHypothesisSetItem ::= SEQUENCE {
    coMPCellID                      ECGI,
    coMPHypothesis                  BIT STRING (SIZE(6..4400, ...)),
    iE-Extensions                   ProtocolExtensionContainer { { CoMPHypothesisSetItem-ExtIEs} } OPTIONAL,
    ...
}

CoMPHypothesisSetItem-ExtIEs X2AP-PROTOCOL-EXTENSION ::= {
    ...
}

CoMPInformation ::= SEQUENCE {
    coMPInformationItem                     CoMPInformationItem,
    coMPInformationStartTime                CoMPInformationStartTime,
    iE-Extensions                           ProtocolExtensionContainer { { CoMPInformation-ExtIEs} } OPTIONAL,
    ...
}

CoMPInformation-ExtIEs X2AP-PROTOCOL-EXTENSION ::= {
    ...
}

CoMPInformationItem ::= SEQUENCE (SIZE(1..maxnoofCoMPHypothesisSet)) OF
    SEQUENCE {
        coMPHypothesisSet                   CoMPHypothesisSet,
        benefitMetric                       BenefitMetric,
        iE-Extensions                       ProtocolExtensionContainer { { CoMPInformationItem-ExtIEs} } OPTIONAL,
        ...
    }

CoMPInformationItem-ExtIEs X2AP-PROTOCOL-EXTENSION ::= {
    ...
}

CoMPInformationStartTime ::= SEQUENCE (SIZE(0..1)) OF
    SEQUENCE {
        startSFN                            INTEGER (0..1023, ...),
        startSubframeNumber                 INTEGER (0..9, ...), 
        iE-Extensions                       ProtocolExtensionContainer { { CoMPInformationStartTime-ExtIEs} } OPTIONAL,
        ...
    }

CoMPInformationStartTime-ExtIEs X2AP-PROTOCOL-EXTENSION ::= {
    ...
}

CompositeAvailableCapacityGroup ::= SEQUENCE {
    dL-CompositeAvailableCapacity                   CompositeAvailableCapacity,
    uL-CompositeAvailableCapacity                   CompositeAvailableCapacity,
    iE-Extensions                                   ProtocolExtensionContainer { { CompositeAvailableCapacityGroup-ExtIEs} } OPTIONAL,
    ...
}

CompositeAvailableCapacityGroup-ExtIEs X2AP-PROTOCOL-EXTENSION ::= {
    ...
}

CompositeAvailableCapacity ::= SEQUENCE {
    cellCapacityClassValue                          CellCapacityClassValue              OPTIONAL,
    capacityValue                                   CapacityValue,
    iE-Extensions                                   ProtocolExtensionContainer { { CompositeAvailableCapacity-ExtIEs} } OPTIONAL,
    ...
}

CompositeAvailableCapacity-ExtIEs X2AP-PROTOCOL-EXTENSION ::= {
    ...
}

COUNTvalue ::= SEQUENCE {
    pDCP-SN                 PDCP-SN,
    hFN                     HFN,
    iE-Extensions           ProtocolExtensionContainer { { COUNTvalue-ExtIEs} } OPTIONAL,
    ...
}

COUNTvalue-ExtIEs X2AP-PROTOCOL-EXTENSION ::= {
    ...
}

COUNTValueExtended ::= SEQUENCE {
    pDCP-SNExtended         PDCP-SNExtended,
    hFNModified             HFNModified,
    iE-Extensions           ProtocolExtensionContainer { { COUNTValueExtended-ExtIEs} } OPTIONAL,
    ...
}

COUNTValueExtended-ExtIEs X2AP-PROTOCOL-EXTENSION ::= {
    ...
}

CriticalityDiagnostics ::= SEQUENCE {
    procedureCode                   ProcedureCode                   OPTIONAL,
    triggeringMessage               TriggeringMessage               OPTIONAL,
    procedureCriticality            Criticality                     OPTIONAL,
    iEsCriticalityDiagnostics       CriticalityDiagnostics-IE-List  OPTIONAL,
    iE-Extensions                   ProtocolExtensionContainer { {CriticalityDiagnostics-ExtIEs} }  OPTIONAL,
    ...
}


CriticalityDiagnostics-ExtIEs X2AP-PROTOCOL-EXTENSION ::= {
    ...
}

CriticalityDiagnostics-IE-List ::= SEQUENCE (SIZE (1..maxNrOfErrors)) OF
    SEQUENCE {
        iECriticality           Criticality,
        iE-ID                   ProtocolIE-ID,
        typeOfError             TypeOfError,
        iE-Extensions           ProtocolExtensionContainer { {CriticalityDiagnostics-IE-List-ExtIEs} } OPTIONAL,
        ...
}

CriticalityDiagnostics-IE-List-ExtIEs X2AP-PROTOCOL-EXTENSION ::= {
    ...
}

CRNTI ::= BIT STRING (SIZE (16))

CSGMembershipStatus ::= ENUMERATED { 
    member,
    not-member
}

CSG-Id ::= BIT STRING (SIZE (27))

CyclicPrefixDL ::= ENUMERATED { 
    normal,
    extended,
    ...
}

CyclicPrefixUL ::= ENUMERATED { 
    normal,
    extended,
    ...
}


-- D

DeactivationIndication::= ENUMERATED { 
    deactivated,
    ...
}

DL-Forwarding ::= ENUMERATED {
    dL-forwardingProposed,
    ...
}

DL-GBR-PRB-usage::= INTEGER (0..100)

DL-non-GBR-PRB-usage::= INTEGER (0..100)

DL-Total-PRB-usage::= INTEGER (0..100)

DynamicDLTransmissionInformation ::= CHOICE {
    naics-active            DynamicNAICSInformation,
    naics-inactive          NULL,
    ...
}

DynamicNAICSInformation ::= SEQUENCE {
    transmissionModes                   BIT STRING (SIZE(8))                                                OPTIONAL,
    pB-information                      INTEGER(0..3)                                                       OPTIONAL,
    pA-list                             SEQUENCE (SIZE(0..maxnoofPA)) OF PA-Values,
    iE-Extensions                       ProtocolExtensionContainer { {DynamicNAICSInformation-ExtIEs} } OPTIONAL,
    ...
}

DynamicNAICSInformation-ExtIEs X2AP-PROTOCOL-EXTENSION ::= {
    ...
}

-- E

EARFCN ::= INTEGER (0..maxEARFCN)

EARFCNExtension ::= INTEGER(maxEARFCNPlusOne..newmaxEARFCN, ...)

FDD-Info ::= SEQUENCE {
    uL-EARFCN                       EARFCN,
    dL-EARFCN                       EARFCN,
    uL-Transmission-Bandwidth       Transmission-Bandwidth,
    dL-Transmission-Bandwidth       Transmission-Bandwidth,
    iE-Extensions               ProtocolExtensionContainer { {FDD-Info-ExtIEs} } OPTIONAL,
    ...
}

FDD-Info-ExtIEs X2AP-PROTOCOL-EXTENSION ::= {
    { ID id-UL-EARFCNExtension      CRITICALITY reject  EXTENSION EARFCNExtension       PRESENCE optional}|
    { ID id-DL-EARFCNExtension      CRITICALITY reject  EXTENSION EARFCNExtension       PRESENCE optional},
    ...
}

TDD-Info ::= SEQUENCE {
    eARFCN                          EARFCN,
    transmission-Bandwidth          Transmission-Bandwidth,
    subframeAssignment              SubframeAssignment,
    specialSubframe-Info                SpecialSubframe-Info,
    iE-Extensions               ProtocolExtensionContainer { {TDD-Info-ExtIEs} } OPTIONAL,
    ...
}
TDD-Info-ExtIEs X2AP-PROTOCOL-EXTENSION ::= {
    { ID id-AdditionalSpecialSubframe-Info  CRITICALITY ignore  EXTENSION AdditionalSpecialSubframe-Info    PRESENCE optional}|
    { ID id-eARFCNExtension                 CRITICALITY reject  EXTENSION EARFCNExtension                       PRESENCE optional},
    ...
}

EUTRA-Mode-Info ::= CHOICE {
    fDD     FDD-Info,
    tDD     TDD-Info,
    ...
}

ECGI ::= SEQUENCE {
    pLMN-Identity               PLMN-Identity,
    eUTRANcellIdentifier        EUTRANCellIdentifier,
    iE-Extensions               ProtocolExtensionContainer { {ECGI-ExtIEs} } OPTIONAL,
    ...
}

ECGI-ExtIEs X2AP-PROTOCOL-EXTENSION ::= {
    ...
}

ENB-ID ::= CHOICE {
    macro-eNB-ID    BIT STRING (SIZE (20)),
    home-eNB-ID     BIT STRING (SIZE (28)),
    ...
}

EncryptionAlgorithms ::= BIT STRING (SIZE (16, ...))

EPLMNs ::= SEQUENCE (SIZE(1..maxnoofEPLMNs)) OF PLMN-Identity

E-RAB-ID ::= INTEGER (0..15, ...)

E-RAB-Level-QoS-Parameters ::= SEQUENCE {
    qCI                             QCI,
    allocationAndRetentionPriority  AllocationAndRetentionPriority,
    gbrQosInformation               GBR-QosInformation                                                  OPTIONAL,
    iE-Extensions                   ProtocolExtensionContainer { { E-RAB-Level-QoS-Parameters-ExtIEs} } OPTIONAL,
    ...
}

E-RAB-Level-QoS-Parameters-ExtIEs X2AP-PROTOCOL-EXTENSION ::= {
    ...
}

E-RAB-List ::= SEQUENCE (SIZE(1.. maxnoofBearers)) OF ProtocolIE-Single-Container { {E-RAB-ItemIEs} }

E-RAB-ItemIEs   X2AP-PROTOCOL-IES ::= {
    { ID id-E-RAB-Item   CRITICALITY ignore     TYPE E-RAB-Item     PRESENCE mandatory },
    ...
}

E-RAB-Item ::= SEQUENCE {
    e-RAB-ID                E-RAB-ID,
    cause                       Cause,
    iE-Extensions               ProtocolExtensionContainer { {E-RAB-Item-ExtIEs} } OPTIONAL,
    ...
}

E-RAB-Item-ExtIEs X2AP-PROTOCOL-EXTENSION ::= {
    ...
}

EUTRANCellIdentifier ::= BIT STRING (SIZE (28))

EUTRANTraceID       ::= OCTET STRING (SIZE (8))


EventType ::= ENUMERATED{
    change-of-serving-cell,
    ...
}

ExpectedUEBehaviour ::= SEQUENCE {
    expectedActivity        ExpectedUEActivityBehaviour OPTIONAL,
    expectedHOInterval      ExpectedHOInterval          OPTIONAL,
    iE-Extensions           ProtocolExtensionContainer { { ExpectedUEBehaviour-ExtIEs} } OPTIONAL,
    ...
}

ExpectedUEBehaviour-ExtIEs X2AP-PROTOCOL-EXTENSION ::= {
    ...
}

ExpectedUEActivityBehaviour ::= SEQUENCE {
    expectedActivityPeriod                  ExpectedActivityPeriod                  OPTIONAL,
    expectedIdlePeriod                      ExpectedIdlePeriod                      OPTIONAL,
    sourceofUEActivityBehaviourInformation  SourceOfUEActivityBehaviourInformation  OPTIONAL,
    iE-Extensions       ProtocolExtensionContainer { { ExpectedUEActivityBehaviour-ExtIEs} } OPTIONAL,
    ...
}

ExpectedUEActivityBehaviour-ExtIEs X2AP-PROTOCOL-EXTENSION ::= {
    ...
}

ExpectedActivityPeriod ::= INTEGER (1..30|40|50|60|80|100|120|150|180|181,...)

ExpectedIdlePeriod ::= INTEGER (1..30|40|50|60|80|100|120|150|180|181,...)

SourceOfUEActivityBehaviourInformation ::= ENUMERATED {
    subscription-information,
    statistics,
    ...
}

ExpectedHOInterval ::= ENUMERATED {
    sec15, sec30, sec60, sec90, sec120, sec180, long-time,
    ...
}

ExtendedULInterferenceOverloadInfo ::= SEQUENCE {
    associatedSubframes                         BIT STRING (SIZE (5)),
    extended-ul-InterferenceOverloadIndication  UL-InterferenceOverloadIndication,
    iE-Extensions                               ProtocolExtensionContainer { { ExtendedULInterferenceOverloadInfo-ExtIEs} } OPTIONAL,
    ...
}

ExtendedULInterferenceOverloadInfo-ExtIEs X2AP-PROTOCOL-EXTENSION ::= {
    ...
}

-- F

ForbiddenInterRATs ::= ENUMERATED {
    all,
    geran,
    utran,
    cdma2000,
    ...,
    geranandutran,
    cdma2000andutran

}

ForbiddenTAs ::= SEQUENCE (SIZE(1.. maxnoofEPLMNsPlusOne)) OF ForbiddenTAs-Item

ForbiddenTAs-Item ::= SEQUENCE {
    pLMN-Identity       PLMN-Identity,
    forbiddenTACs       ForbiddenTACs,
    iE-Extensions       ProtocolExtensionContainer { {ForbiddenTAs-Item-ExtIEs} } OPTIONAL,
    ...
}

ForbiddenTAs-Item-ExtIEs X2AP-PROTOCOL-EXTENSION ::= {
    ...
}

ForbiddenTACs ::= SEQUENCE (SIZE(1..maxnoofForbTACs)) OF TAC

ForbiddenLAs ::= SEQUENCE (SIZE(1..maxnoofEPLMNsPlusOne)) OF ForbiddenLAs-Item

ForbiddenLAs-Item ::= SEQUENCE {    
    pLMN-Identity       PLMN-Identity,
    forbiddenLACs       ForbiddenLACs,
    iE-Extensions       ProtocolExtensionContainer { {ForbiddenLAs-Item-ExtIEs} } OPTIONAL,
    ...
}

ForbiddenLAs-Item-ExtIEs X2AP-PROTOCOL-EXTENSION ::= {
    ...
}

ForbiddenLACs ::= SEQUENCE (SIZE(1..maxnoofForbLACs)) OF LAC

Fourframes ::= BIT STRING (SIZE (24))

FreqBandIndicator ::= INTEGER (1..256, ...)

-- G

GBR-QosInformation ::= SEQUENCE {
    e-RAB-MaximumBitrateDL          BitRate,
    e-RAB-MaximumBitrateUL          BitRate,
    e-RAB-GuaranteedBitrateDL       BitRate,
    e-RAB-GuaranteedBitrateUL       BitRate,
    iE-Extensions                   ProtocolExtensionContainer { { GBR-QosInformation-ExtIEs} } OPTIONAL,
    ...
}

GBR-QosInformation-ExtIEs X2AP-PROTOCOL-EXTENSION ::= {
    ...
}

GlobalENB-ID ::= SEQUENCE {
    pLMN-Identity           PLMN-Identity,
    eNB-ID                  ENB-ID,
    iE-Extensions           ProtocolExtensionContainer { {GlobalENB-ID-ExtIEs} } OPTIONAL,
    ...
}

GlobalENB-ID-ExtIEs X2AP-PROTOCOL-EXTENSION ::= {
    ...
}

GTPtunnelEndpoint ::= SEQUENCE {
    transportLayerAddress           TransportLayerAddress,
    gTP-TEID                        GTP-TEI,
    iE-Extensions                   ProtocolExtensionContainer { {GTPtunnelEndpoint-ExtIEs} } OPTIONAL,
    ...
}

GTPtunnelEndpoint-ExtIEs X2AP-PROTOCOL-EXTENSION ::= {
    ...
}

GTP-TEI                 ::= OCTET STRING (SIZE (4))

GUGroupIDList       ::= SEQUENCE (SIZE (1..maxPools)) OF GU-Group-ID


GU-Group-ID         ::= SEQUENCE {
    pLMN-Identity       PLMN-Identity,
    mME-Group-ID        MME-Group-ID,
    iE-Extensions       ProtocolExtensionContainer { {GU-Group-ID-ExtIEs} } OPTIONAL,
    ...
}

GU-Group-ID-ExtIEs X2AP-PROTOCOL-EXTENSION ::= {
    ...
}


GUMMEI          ::= SEQUENCE {
    
    gU-Group-ID     GU-Group-ID,
    mME-Code            MME-Code,
    iE-Extensions                   ProtocolExtensionContainer { {GUMMEI-ExtIEs} } OPTIONAL,
    ...
}

GUMMEI-ExtIEs X2AP-PROTOCOL-EXTENSION ::= {
    ...
}



-- H

HandoverReportType ::= ENUMERATED {
    hoTooEarly,
    hoToWrongCell,
    ...,
    interRATpingpong
}

HandoverRestrictionList ::= SEQUENCE {
    servingPLMN                 PLMN-Identity,
    equivalentPLMNs             EPLMNs                  OPTIONAL,
    forbiddenTAs                ForbiddenTAs            OPTIONAL,
    forbiddenLAs                ForbiddenLAs            OPTIONAL,
    forbiddenInterRATs          ForbiddenInterRATs      OPTIONAL,
    iE-Extensions               ProtocolExtensionContainer { {HandoverRestrictionList-ExtIEs} } OPTIONAL,
    ...
}

HandoverRestrictionList-ExtIEs X2AP-PROTOCOL-EXTENSION ::= {
    ...
}

HFN ::= INTEGER (0..1048575)

HFNModified ::= INTEGER (0..131071)

HWLoadIndicator ::= SEQUENCE {
    dLHWLoadIndicator           LoadIndicator,
    uLHWLoadIndicator           LoadIndicator,
    iE-Extensions               ProtocolExtensionContainer { { HWLoadIndicator-ExtIEs} } OPTIONAL,
    ...
}

HWLoadIndicator-ExtIEs X2AP-PROTOCOL-EXTENSION ::= {
    ...
}


-- I

Masked-IMEISV ::= BIT STRING (SIZE (64))

InvokeIndication ::= ENUMERATED{
    abs-information,
    ...,
    naics-information-start,
    naics-information-stop
}

IntegrityProtectionAlgorithms ::= BIT STRING (SIZE (16, ...))

InterfacesToTrace ::= BIT STRING (SIZE (8)) 
-- J
-- K


Key-eNodeB-Star ::= BIT STRING (SIZE(256))

-- L


LAC                 ::= OCTET STRING (SIZE (2)) --(EXCEPT ('0000'H|'FFFE'H))

LastVisitedCell-Item ::= CHOICE {
    e-UTRAN-Cell                    LastVisitedEUTRANCellInformation,
    uTRAN-Cell                      LastVisitedUTRANCellInformation,
    gERAN-Cell                      LastVisitedGERANCellInformation,
    ...
}

LastVisitedEUTRANCellInformation ::= SEQUENCE {
    global-Cell-ID                  ECGI,
    cellType                        CellType,
    time-UE-StayedInCell            Time-UE-StayedInCell,
    iE-Extensions                   ProtocolExtensionContainer { { LastVisitedEUTRANCellInformation-ExtIEs} } OPTIONAL,
    ...
}

LastVisitedEUTRANCellInformation-ExtIEs X2AP-PROTOCOL-EXTENSION ::= {
-- Extension for Rel-11 to support enhanced granularity for time UE stayed in cell --
    { ID id-Time-UE-StayedInCell-EnhancedGranularity    CRITICALITY ignore  EXTENSION Time-UE-StayedInCell-EnhancedGranularity  PRESENCE optional}|
    { ID id-HO-cause                                    CRITICALITY ignore  EXTENSION Cause                         PRESENCE optional},
    ...
}

LastVisitedUTRANCellInformation ::= OCTET STRING

LastVisitedGERANCellInformation ::= CHOICE {
    undefined                       NULL,
    ...
}

Links-to-log ::= ENUMERATED {uplink, downlink, both-uplink-and-downlink, ...}

LoadIndicator ::= ENUMERATED {
    lowLoad,
    mediumLoad, 
    highLoad,
    overLoad,
    ...
}



LocationReportingInformation ::= SEQUENCE {
    eventType       EventType,
    reportArea      ReportArea,
    iE-Extensions       ProtocolExtensionContainer { {LocationReportingInformation-ExtIEs} } OPTIONAL,
    ...
}

LocationReportingInformation-ExtIEs X2AP-PROTOCOL-EXTENSION ::={
    ...
}

-- M

M3Configuration ::= SEQUENCE {
    m3period            M3period,
    iE-Extensions       ProtocolExtensionContainer { { M3Configuration-ExtIEs} } OPTIONAL,
    ...
}

M3Configuration-ExtIEs X2AP-PROTOCOL-EXTENSION ::= {
    ...
}

M3period ::= ENUMERATED {ms100, ms1000, ms10000, ... } 

M4Configuration ::= SEQUENCE {
    m4period            M4period,
    m4-links-to-log     Links-to-log,
    iE-Extensions       ProtocolExtensionContainer { { M4Configuration-ExtIEs} } OPTIONAL,
    ...
}

M4Configuration-ExtIEs X2AP-PROTOCOL-EXTENSION ::= {
    ...
}

M4period ::= ENUMERATED {ms1024, ms2048, ms5120, ms10240, min1, ... } 


M5Configuration ::= SEQUENCE {
    m5period            M5period,
    m5-links-to-log     Links-to-log,
    iE-Extensions       ProtocolExtensionContainer { { M5Configuration-ExtIEs} } OPTIONAL,
    ...
}

M5Configuration-ExtIEs X2AP-PROTOCOL-EXTENSION ::= {
    ...
}

M5period ::= ENUMERATED {ms1024, ms2048, ms5120, ms10240, min1, ... }

MDT-Activation      ::= ENUMERATED { 
    immediate-MDT-only,
    immediate-MDT-and-Trace,
    ...
}

MDT-Configuration ::= SEQUENCE {
    mdt-Activation              MDT-Activation,
    areaScopeOfMDT              AreaScopeOfMDT,
    measurementsToActivate      MeasurementsToActivate,
    m1reportingTrigger          M1ReportingTrigger,
    m1thresholdeventA2          M1ThresholdEventA2          OPTIONAL,
-- Included in case of event-triggered, or event-triggered periodic reporting for measurement M1
    m1periodicReporting         M1PeriodicReporting         OPTIONAL,
-- Included in case of periodic, or event-triggered periodic reporting for measurement M1
    iE-Extensions               ProtocolExtensionContainer { { MDT-Configuration-ExtIEs} } OPTIONAL,
    ...
}

MDT-Configuration-ExtIEs X2AP-PROTOCOL-EXTENSION ::= {
    {ID id-M3Configuration              CRITICALITY ignore  EXTENSION M3Configuration       PRESENCE conditional}|
    {ID id-M4Configuration              CRITICALITY ignore  EXTENSION M4Configuration       PRESENCE conditional}|
    {ID id-M5Configuration              CRITICALITY ignore  EXTENSION M5Configuration       PRESENCE conditional}|
    {ID id-MDT-Location-Info            CRITICALITY ignore  EXTENSION MDT-Location-Info     PRESENCE optional}|
    {ID id-SignallingBasedMDTPLMNList   CRITICALITY ignore  EXTENSION MDTPLMNList           PRESENCE optional},
    ...
}

MDTPLMNList ::= SEQUENCE (SIZE(1..maxnoofMDTPLMNs)) OF PLMN-Identity

MDT-Location-Info ::= BIT STRING (SIZE (8))

MeasurementsToActivate::= BIT STRING (SIZE (8))

MeasurementThresholdA2 ::= CHOICE { 
    threshold-RSRP              Threshold-RSRP,
    threshold-RSRQ              Threshold-RSRQ,
    ...
}

MeNBtoSeNBContainer  ::= OCTET STRING

MME-Group-ID    ::= OCTET STRING (SIZE (2))

MME-Code        ::= OCTET STRING (SIZE (1))

Measurement-ID  ::= INTEGER (1..4095, ...) 

MBMS-Service-Area-Identity-List ::= SEQUENCE (SIZE(1.. maxnoofMBMSServiceAreaIdentities)) OF MBMS-Service-Area-Identity

MBMS-Service-Area-Identity ::= OCTET STRING (SIZE (2))

MBSFN-Subframe-Infolist::= SEQUENCE (SIZE(1.. maxnoofMBSFN)) OF MBSFN-Subframe-Info

MBSFN-Subframe-Info ::= SEQUENCE {
    radioframeAllocationPeriod      RadioframeAllocationPeriod,
    radioframeAllocationOffset      RadioframeAllocationOffset,
    subframeAllocation              SubframeAllocation,
    iE-Extensions           ProtocolExtensionContainer { { MBSFN-Subframe-Info-ExtIEs } }   OPTIONAL,
    ...
}

MBSFN-Subframe-Info-ExtIEs X2AP-PROTOCOL-EXTENSION ::= {
    ...
}

ManagementBasedMDTallowed ::= ENUMERATED {allowed, ...}

MobilityParametersModificationRange ::= SEQUENCE {
    handoverTriggerChangeLowerLimit     INTEGER (-20..20),
    handoverTriggerChangeUpperLimit     INTEGER (-20..20),
    ...
}

MobilityParametersInformation ::= SEQUENCE {
    handoverTriggerChange           INTEGER (-20..20),
    ...
}

MultibandInfoList ::= SEQUENCE (SIZE(1..maxnoofBands)) OF BandInfo 


BandInfo    ::= SEQUENCE {
    freqBandIndicator       FreqBandIndicator,
    iE-Extensions           ProtocolExtensionContainer { { BandInfo-ExtIEs } }  OPTIONAL,
    ...
}

BandInfo-ExtIEs X2AP-PROTOCOL-EXTENSION ::= {
    ...
}

-- N

Neighbour-Information ::= SEQUENCE (SIZE (0..maxnoofNeighbours)) OF SEQUENCE {
    eCGI                        ECGI,
    pCI                     PCI,
    eARFCN                      EARFCN,
    iE-Extensions        ProtocolExtensionContainer { {Neighbour-Information-ExtIEs} } OPTIONAL,
    ...
}

Neighbour-Information-ExtIEs X2AP-PROTOCOL-EXTENSION ::= {
    { ID id-NeighbourTAC        CRITICALITY ignore  EXTENSION TAC               PRESENCE optional}|
    { ID id-eARFCNExtension     CRITICALITY reject  EXTENSION EARFCNExtension   PRESENCE optional},
    ...
}

NextHopChainingCount ::= INTEGER (0..7)

Number-of-Antennaports ::= ENUMERATED {
        an1,
        an2,
        an4,
        ...
}

-- O

Oneframe ::= BIT STRING (SIZE (6))

-- P

PA-Values ::= ENUMERATED {
    dB-6,
    dB-4dot77,
    dB-3,
    dB-1dot77,
    dB0,
    dB1,
    dB2,
    dB3,
    ...
}

PDCP-SN ::= INTEGER (0..4095)

PDCP-SNExtended ::= INTEGER (0..32767)

PCI ::= INTEGER (0..503, ...)

M1PeriodicReporting ::= SEQUENCE { 
    reportInterval              ReportIntervalMDT,
    reportAmount                ReportAmountMDT,
    iE-Extensions               ProtocolExtensionContainer { { M1PeriodicReporting-ExtIEs} } OPTIONAL,
    ...
}

M1PeriodicReporting-ExtIEs X2AP-PROTOCOL-EXTENSION ::= {
    ...
}

PLMN-Identity ::= OCTET STRING (SIZE(3))

PRACH-Configuration ::= SEQUENCE {
    rootSequenceIndex                       INTEGER (0..837),
    zeroCorrelationIndex                    INTEGER (0..15),
    highSpeedFlag                           BOOLEAN,
    prach-FreqOffset                        INTEGER (0..94),
    prach-ConfigIndex                       INTEGER (0..63)     OPTIONAL,  -- present for TDD --
    iE-Extensions                           ProtocolExtensionContainer { {PRACH-Configuration-ExtIEs} } OPTIONAL,
    ...
}

PRACH-Configuration-ExtIEs X2AP-PROTOCOL-EXTENSION ::= {
    ...
}

Pre-emptionCapability ::= ENUMERATED {
    shall-not-trigger-pre-emption,
    may-trigger-pre-emption
}

Pre-emptionVulnerability ::= ENUMERATED {
    not-pre-emptable,
    pre-emptable
}

PriorityLevel               ::= INTEGER { spare (0), highest (1), lowest (14), no-priority (15) } (0..15)

-- Q

QCI ::= INTEGER (0..255)

-- R

RadioframeAllocationOffset ::= INTEGER (0..7, ...)

RadioframeAllocationPeriod ::= ENUMERATED{
    n1,
    n2,
    n4,
    n8,
    n16,
    n32,
    ...
}


RadioResourceStatus ::= SEQUENCE {
    dL-GBR-PRB-usage                            DL-GBR-PRB-usage,
    uL-GBR-PRB-usage                            UL-GBR-PRB-usage,
    dL-non-GBR-PRB-usage                        DL-non-GBR-PRB-usage,
    uL-non-GBR-PRB-usage                        UL-non-GBR-PRB-usage,
    dL-Total-PRB-usage                          DL-Total-PRB-usage,
    uL-Total-PRB-usage                          UL-Total-PRB-usage,
    iE-Extensions                               ProtocolExtensionContainer { {RadioResourceStatus-ExtIEs} } OPTIONAL,
    ...
}

RadioResourceStatus-ExtIEs X2AP-PROTOCOL-EXTENSION ::= {
    ...
}

ReceiveStatusofULPDCPSDUs ::= BIT STRING (SIZE(4096))

ReceiveStatusOfULPDCPSDUsExtended ::= BIT STRING (SIZE(1..16384))

Registration-Request    ::= ENUMERATED {
    start,
    stop,
    ...
}
 
RelativeNarrowbandTxPower ::= SEQUENCE {

    rNTP-PerPRB                         BIT STRING (SIZE(6..110, ...)),
    rNTP-Threshold                      RNTP-Threshold,
    numberOfCellSpecificAntennaPorts    ENUMERATED {one, two, four, ...},
    p-B                                 INTEGER (0..3,...),
    pDCCH-InterferenceImpact            INTEGER (0..4,...),
    iE-Extensions                       ProtocolExtensionContainer { { RelativeNarrowbandTxPower-ExtIEs} } OPTIONAL,
    ...
}

RelativeNarrowbandTxPower-ExtIEs X2AP-PROTOCOL-EXTENSION ::= {
    ...
}

ReportAmountMDT ::= ENUMERATED{r1, r2, r4, r8, r16, r32, r64, rinfinity}

ReportArea ::= ENUMERATED{
    ecgi,
    ...
}

ReportingPeriodicityRSRPMR ::= ENUMERATED {
    one-hundred-20-ms,
    two-hundred-40-ms,
    four-hundred-80-ms,
    six-hundred-40-ms,
...
}

ReportIntervalMDT ::= ENUMERATED {ms120, ms240, ms480, ms640, ms1024, ms2048, ms5120, ms10240, min1, min6, min12, min30, min60}

ReportCharacteristics   ::= BIT STRING (SIZE (32))

M1ReportingTrigger::= ENUMERATED{
    periodic,
    a2eventtriggered,
    ...,
    a2eventtriggered-periodic
}

RNTP-Threshold ::= ENUMERATED {
    minusInfinity,
    minusEleven,
    minusTen,
    minusNine,
    minusEight,
    minusSeven,
    minusSix,
    minusFive,
    minusFour,
    minusThree,
    minusTwo,
    minusOne,
    zero,
    one,
    two,
    three,
    ...
}

RRC-Context ::= OCTET STRING

RRCConnReestabIndicator ::= ENUMERATED {
    reconfigurationFailure, handoverFailure, otherFailure, ...
}
-- The values correspond to the values of ReestablishmentCause reported from the UE in the RRCConnectionReestablishmentRequest, as defined in TS 36.331 [9]

RRCConnSetupIndicator::= ENUMERATED {
    rrcConnSetup,
    ...
}

RSRPMeasurementResult ::= SEQUENCE (SIZE(1..maxCellReport)) OF
    SEQUENCE {
        rSRPCellID                      ECGI,
        rSRPMeasured                    INTEGER (0..97, ...), 
        iE-Extensions                   ProtocolExtensionContainer { { RSRPMeasurementResult-ExtIEs} } OPTIONAL,
        ...
    }

RSRPMeasurementResult-ExtIEs X2AP-PROTOCOL-EXTENSION ::= {
    ...
}

RSRPMRList ::= SEQUENCE (SIZE(1..maxUEReport)) OF
    SEQUENCE {
        rSRPMeasurementResult           RSRPMeasurementResult, 
        iE-Extensions                   ProtocolExtensionContainer { { RSRPMRList-ExtIEs} } OPTIONAL,
        ...
    }

RSRPMRList-ExtIEs X2AP-PROTOCOL-EXTENSION ::= {
    ...
}

-- S

S1TNLLoadIndicator ::= SEQUENCE {
    dLS1TNLLoadIndicator            LoadIndicator,
    uLS1TNLLoadIndicator            LoadIndicator,
    iE-Extensions                   ProtocolExtensionContainer { { S1TNLLoadIndicator-ExtIEs} } OPTIONAL,
    ...
}

S1TNLLoadIndicator-ExtIEs X2AP-PROTOCOL-EXTENSION ::= {
    ...
}

SCGChangeIndication ::= ENUMERATED {pDCPCountWrapAround, pSCellChange, other, ...}

SeNBSecurityKey ::= BIT STRING (SIZE(256))

SeNBtoMeNBContainer ::= OCTET STRING


ServedCells ::= SEQUENCE (SIZE (1.. maxCellineNB)) OF SEQUENCE {
    servedCellInfo                  ServedCell-Information,
    neighbour-Info                  Neighbour-Information           OPTIONAL,
    iE-Extensions                   ProtocolExtensionContainer { {ServedCell-ExtIEs} } OPTIONAL,
    ...
}

ServedCell-ExtIEs X2AP-PROTOCOL-EXTENSION ::= {
    ...
}

ServedCell-Information ::= SEQUENCE {
    pCI                 PCI,
    cellId              ECGI,
    tAC                 TAC,
    broadcastPLMNs      BroadcastPLMNs-Item,
    eUTRA-Mode-Info     EUTRA-Mode-Info,
    iE-Extensions       ProtocolExtensionContainer { {ServedCell-Information-ExtIEs} } OPTIONAL,
    ...
}

ServedCell-Information-ExtIEs X2AP-PROTOCOL-EXTENSION ::= {
    { ID id-Number-of-Antennaports      CRITICALITY ignore  EXTENSION Number-of-Antennaports            PRESENCE optional }|
    { ID id-PRACH-Configuration         CRITICALITY ignore  EXTENSION PRACH-Configuration               PRESENCE optional }|
    { ID id-MBSFN-Subframe-Info         CRITICALITY ignore  EXTENSION MBSFN-Subframe-Infolist           PRESENCE optional }|
    { ID id-CSG-Id                      CRITICALITY ignore  EXTENSION CSG-Id                            PRESENCE optional }|
    { ID id-MBMS-Service-Area-List      CRITICALITY ignore  EXTENSION MBMS-Service-Area-Identity-List   PRESENCE optional }|
    { ID id-MultibandInfoList           CRITICALITY ignore  EXTENSION MultibandInfoList                 PRESENCE optional },
    ...
}

ShortMAC-I ::= BIT STRING (SIZE(16))

SRVCCOperationPossible ::= ENUMERATED {
    possible,
    ...
}

SubframeAssignment ::= ENUMERATED { 
    sa0,
    sa1, 
    sa2,
    sa3,
    sa4,
    sa5,
    sa6,
    ...
}

SpecialSubframe-Info ::= SEQUENCE {
    specialSubframePatterns     SpecialSubframePatterns,
    cyclicPrefixDL              CyclicPrefixDL,
    cyclicPrefixUL              CyclicPrefixUL,
    iE-Extensions               ProtocolExtensionContainer { { SpecialSubframe-Info-ExtIEs} } OPTIONAL,
    ...
}

SpecialSubframe-Info-ExtIEs X2AP-PROTOCOL-EXTENSION ::= {
    ...
}


SpecialSubframePatterns ::= ENUMERATED { 
    ssp0,
    ssp1, 
    ssp2,
    ssp3,
    ssp4,
    ssp5,
    ssp6,
    ssp7,
    ssp8,
    ...
}

SubscriberProfileIDforRFP ::= INTEGER (1..256) 

SubframeAllocation ::= CHOICE {
    oneframe                        Oneframe,
    fourframes                      Fourframes,
    ...
}

-- T

TAC ::= OCTET STRING (SIZE (2)) 

TABasedMDT::= SEQUENCE {
    tAListforMDT        TAListforMDT,
    iE-Extensions       ProtocolExtensionContainer { {TABasedMDT-ExtIEs} } OPTIONAL,
    ...
}

TABasedMDT-ExtIEs X2AP-PROTOCOL-EXTENSION ::= {
    ...
}

TAListforMDT ::= SEQUENCE (SIZE(1..maxnoofTAforMDT)) OF TAC

TAIBasedMDT ::= SEQUENCE {
    tAIListforMDT           TAIListforMDT,
    iE-Extensions           ProtocolExtensionContainer { {TAIBasedMDT-ExtIEs} } OPTIONAL,
    ...
}

TAIBasedMDT-ExtIEs X2AP-PROTOCOL-EXTENSION ::= {
    ...
}

TAIListforMDT ::= SEQUENCE (SIZE(1..maxnoofTAforMDT)) OF TAI-Item

TAI-Item ::= SEQUENCE {
    tAC                 TAC,
    pLMN-Identity       PLMN-Identity,
    iE-Extensions       ProtocolExtensionContainer { { TAI-Item-ExtIEs} } OPTIONAL,
    ...
}

TAI-Item-ExtIEs X2AP-PROTOCOL-EXTENSION ::= {
    ...
}

TargetCellInUTRAN ::= OCTET STRING -- This IE is to be encoded according to the UTRAN Cell ID in the Last Visited UTRAN Cell Information IE in TS 25.413 [24]

M1ThresholdEventA2 ::= SEQUENCE { 
    measurementThreshold        MeasurementThresholdA2,
    iE-Extensions               ProtocolExtensionContainer { { M1ThresholdEventA2-ExtIEs} } OPTIONAL,
    ...
}

M1ThresholdEventA2-ExtIEs X2AP-PROTOCOL-EXTENSION ::= {
    ...
}

TargeteNBtoSource-eNBTransparentContainer   ::= OCTET STRING

Threshold-RSRP ::= INTEGER(0..97)

Threshold-RSRQ ::= INTEGER(0..34)

TimeToWait ::= ENUMERATED {
    v1s, 
    v2s, 
    v5s, 
    v10s, 
    v20s, 
    v60s, 
    ...
}

Time-UE-StayedInCell ::= INTEGER (0..4095)

Time-UE-StayedInCell-EnhancedGranularity ::= INTEGER (0..40950)


TraceActivation ::= SEQUENCE {
    eUTRANTraceID                   EUTRANTraceID,
    interfacesToTrace               InterfacesToTrace,
traceDepth                      TraceDepth,
traceCollectionEntityIPAddress  TraceCollectionEntityIPAddress,
    iE-Extensions                   ProtocolExtensionContainer { {TraceActivation-ExtIEs} } OPTIONAL,
    ...
}

TraceActivation-ExtIEs X2AP-PROTOCOL-EXTENSION ::= {
    { ID id-MDTConfiguration    CRITICALITY ignore  EXTENSION MDT-Configuration     PRESENCE optional},
    ...
}

TraceCollectionEntityIPAddress ::= BIT STRING (SIZE(1..160, ...))

TraceDepth      ::= ENUMERATED { 
    minimum,
    medium,
    maximum,
    minimumWithoutVendorSpecificExtension,
    mediumWithoutVendorSpecificExtension,
    maximumWithoutVendorSpecificExtension,
    ...
}




Transmission-Bandwidth ::= ENUMERATED {
        bw6,
        bw15,
        bw25,
        bw50,
        bw75,
        bw100,
        ...
}

TransportLayerAddress           ::= BIT STRING (SIZE(1..160, ...))

TypeOfError ::= ENUMERATED {
    not-understood,
    missing,
    ...
}


-- U

UE-HistoryInformation ::= SEQUENCE (SIZE(1..maxnoofCells)) OF LastVisitedCell-Item

UE-HistoryInformationFromTheUE ::= OCTET STRING
-- This IE is a transparent container and shall be encoded as the VisitedCellInfoList field contained in the UEInformationResponse message as defined in TS 36.331 [9]

UE-S1AP-ID                  ::= INTEGER (0.. 4294967295)

UE-X2AP-ID                  ::= INTEGER (0..4095)

UEAggregateMaximumBitRate ::= SEQUENCE {
    uEaggregateMaximumBitRateDownlink   BitRate,
    uEaggregateMaximumBitRateUplink     BitRate,
    iE-Extensions                       ProtocolExtensionContainer { {UEAggregate-MaximumBitrate-ExtIEs} } OPTIONAL,
    ...
}

UEAggregate-MaximumBitrate-ExtIEs X2AP-PROTOCOL-EXTENSION ::= {
    ...
}

UESecurityCapabilities ::= SEQUENCE {
    encryptionAlgorithms                EncryptionAlgorithms,
    integrityProtectionAlgorithms       IntegrityProtectionAlgorithms,
    iE-Extensions                       ProtocolExtensionContainer { { UESecurityCapabilities-ExtIEs} }     OPTIONAL,
...
}

UESecurityCapabilities-ExtIEs X2AP-PROTOCOL-EXTENSION ::= {
    ...
}

UL-GBR-PRB-usage::= INTEGER (0..100)

UL-non-GBR-PRB-usage::= INTEGER (0..100)

UL-Total-PRB-usage::= INTEGER (0..100)

UL-InterferenceOverloadIndication ::= SEQUENCE (SIZE(1..maxnoofPRBs)) OF UL-InterferenceOverloadIndication-Item

UL-InterferenceOverloadIndication-Item ::= ENUMERATED {
    high-interference,
    medium-interference,
    low-interference,
    ...
}

UL-HighInterferenceIndicationInfo ::= SEQUENCE (SIZE(1..maxCellineNB)) OF UL-HighInterferenceIndicationInfo-Item

UL-HighInterferenceIndicationInfo-Item ::= SEQUENCE {
    target-Cell-ID                  ECGI,
    ul-interferenceindication       UL-HighInterferenceIndication,
    iE-Extensions                   ProtocolExtensionContainer { { UL-HighInterferenceIndicationInfo-Item-ExtIEs} } OPTIONAL,
    ...
}

UL-HighInterferenceIndicationInfo-Item-ExtIEs X2AP-PROTOCOL-EXTENSION ::= {
    ...
}

UL-HighInterferenceIndication ::= BIT STRING (SIZE(1..110, ...))

UE-RLF-Report-Container::= OCTET STRING
-- This IE is a transparent container and shall be encoded as the RLF-Report-r9 field contained in the UEInformationResponse message as defined in TS 36.331 [9]

UE-RLF-Report-Container-for-extended-bands ::= OCTET STRING
-- This IE is a transparent container and shall be encoded as the RLF-Report-v9e0 field contained in the UEInformationResponse message as defined in TS 36.331 [9]

UsableABSInformation ::= CHOICE {
    fdd                 UsableABSInformationFDD,
    tdd                 UsableABSInformationTDD,
    ...
}

UsableABSInformationFDD ::= SEQUENCE {
    usable-abs-pattern-info             BIT STRING (SIZE(40)),
    iE-Extensions                       ProtocolExtensionContainer { { UsableABSInformationFDD-ExtIEs} } OPTIONAL,
    ...
}

UsableABSInformationFDD-ExtIEs X2AP-PROTOCOL-EXTENSION ::= {
    ...
}

UsableABSInformationTDD ::= SEQUENCE {
    usaable-abs-pattern-info            BIT STRING (SIZE(1..70, ...)),
    iE-Extensions                       ProtocolExtensionContainer { { UsableABSInformationTDD-ExtIEs} } OPTIONAL,
    ...
}

UsableABSInformationTDD-ExtIEs X2AP-PROTOCOL-EXTENSION ::= {
    ...
}

-- V
-- W
-- X
-- Y
-- Z

END
